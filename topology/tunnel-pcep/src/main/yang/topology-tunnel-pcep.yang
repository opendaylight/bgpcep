module topology-tunnel-pcep {
	yang-version 1;
	namespace "urn:opendaylight:params:xml:ns:yang:topology:tunnel:pcep";
	prefix "pceptun";

	import ieee754 { prefix ieee754; revision-date 2013-08-19; }
	import network-topology { prefix nt; revision-date 2013-10-21; }
	import pcep-types { prefix pcep; revision-date 2013-10-05; }
	import rsvp { prefix rsvp; revision-date 2013-08-20; }
	import topology-tunnel { prefix tt; revision-date 2013-08-19; }
	import topology-tunnel-p2p { prefix p2p; revision-date 2013-08-19; }

	organization "Cisco Systems, Inc.";
	contact "Robert Varga <rovarga@cisco.com>";

	description
		"This module contains the Segment Routing extensions to
		base tunnel topology model.

		Copyright (c)2013 Cisco Systems, Inc. All rights reserved.";

	revision "2013-08-20" {
		description
			"Initial revision.";
		reference "";
	}

	typedef administrative-status {
		type enumeration {
			enum active;
			enum inactive;
		}
		reference "https://tools.ietf.org/html/draft-ietf-pce-stateful-pce-05#section-7.3";
	}

	typedef operational-status {
		type enumeration {
			enum down;
			enum up;
			enum active;
			enum going-down;
			enum going-up;
		}
		reference "https://tools.ietf.org/html/draft-ietf-pce-stateful-pce-05#section-7.3";
	}

	grouping tunnel-pcep-type {
		container pcep-tunnel {
			presence "indicates a link is a PCEP tunnel";
		}
	}

	augment "/nt:network-topology/nt:topology/nt:link/tt:tunnel-types" {
		uses tunnel-pcep-type;
	}

	grouping tunnel-pcep-link-attributes {
		leaf administrative-status {
			type administrative-status;
		}

		leaf operational-status {
			type operational-status;
			config false;
		}

		leaf class-type {
			type pcep:class-type;
		}

		leaf bandwidth {
			type ieee754:float32;
		}
	}

	grouping tunnel-pcep-path-attributes {
		leaf administrative-status {
			type administrative-status;
		}

		leaf operational-status {
			type operational-status;
			config false;
		}
	}

	augment "/nt:network-topology/nt:topology/nt:link" {
		when "../../tunnel-types/pcep-tunnel";
		uses tunnel-pcep-link-attributes;
	}

	augment "/nt:network-topology/nt:topology/tt:paths" {
		when "../../tunnel-types/pcep-tunnel";
		uses tunnel-pcep-path-attributes;
	}

	augment "/nt:network-topology/nt:topology/tt:paths/p2p:explicit-hops" {
		when "../../tunnel-types/pcep-tunnel";
		uses rsvp:explicit-route-subobjects;
	}

	augment "/nt:network-topology/nt:topology/tt:paths/p2p:reported-hops" {
		when "../../tunnel-types/pcep-tunnel";
		uses rsvp:record-route-subobjects;
	}
}
