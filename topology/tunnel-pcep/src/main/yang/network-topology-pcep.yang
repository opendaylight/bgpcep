module network-topology-pcep {
	// vi: set et smarttab sw=4 tabstop=4:
	yang-version 1;
	namespace "urn:opendaylight:params:xml:ns:yang:topology:pcep";
	prefix "pn";

	import network-topology { prefix nt; revision-date 2013-10-21; }
	import pcep-types { prefix pcep; revision-date 2013-10-05; }

	organization "Cisco Systems, Inc.";
	contact "Robert Varga <rovarga@cisco.com>";

	description
		"This module contains the PCEP extensions to base topology model. It
        exposes the LSPs for which a particular node is the head end.

		Copyright (c)2013 Cisco Systems, Inc. All rights reserved.";

	revision "2013-10-24" {
		description
			"Initial revision.";
		reference "";
	}

	grouping pcep-client-attributes {
        description "Data present in a node which is a PCEP client (PCC).";

        container pcc {
            config false;

            list lsps {
                leaf name {
                    type pcep:symbolic-path-name;
                }
                key name;

                // FIXME: hide protocol-specific?
                uses pcep:lsp-object;
            }
        }
	}

	augment "/nt:network-topology/nt:topology/nt:node" {
		uses pcep-client-attributes;
	}
}
