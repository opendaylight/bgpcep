// vi: set smarttab et sw=4 tabstop=4:
module config-topology-api {
    yang-version 1;
    namespace "urn:opendaylight:params:xml:ns:yang:controller:topology";
    prefix "topo";

    import config { prefix config; revision-date 2013-04-05; }

    organization "Cisco Systems, Inc.";

    contact "Robert Varga <rovarga@cisco.com>";

    description
        "This module contains the base YANG definitions for
        Topology API.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity topology-reference {
        description
            "Service representing a reference to a topology instance.";

        base "config:service-type";
        config:java-class "org.opendaylight.bgpcep.topology.TopologyReference";
    }
}
