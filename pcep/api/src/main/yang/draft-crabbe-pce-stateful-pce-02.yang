module draft-crabbe-pce-stateful-pce-02 {
	yang-version 1;
	namespace "urn:opendaylight:params:xml:ns:yang:pcep:crabbe:stateful:02";
	prefix "stateful02";

	import ietf-inet-types { prefix inet; revision-date 2010-09-24; }
	import pcep-types { prefix pcep; revision-date 2013-10-05; }
	import pcep-message { prefix msg; revision-date 2013-10-07; }
	import rsvp { prefix rsvp; revision-date 2013-08-20; }

	organization "Cisco Systems, Inc.";
	contact "Dana Kutenicsova <dkutenic@cisco.com>";

	description
		"This module contains the data model of PCEP extensions defined
		in draft-crabbe-pce-stateful-pce.

		Copyright (c)2014 Cisco Systems, Inc. All rights reserved.

		This program and the accompanying materials are made available
		under the terms of the Eclipse Public License v1.0 which
		accompanies this distribution, and is available at
		http://www.eclipse.org/legal/epl-v10.html";

	revision "2014-01-10" {
		description
			"Initial revision.";
		reference "http://tools.ietf.org/html/draft-crabbe-pce-stateful-pce-02";
	}

	typedef plsp-id {
		type uint32 {
			range 0..1048576;
		}
	}

	typedef symbolic-path-name {
		type binary {
			length 1..65535;
		}
	}

	grouping lsp-db-version-tlv {
		description "LSP State Database Version TLV";
		reference "http://tools.ietf.org/html/draft-crabbe-pce-stateful-pce-02#section-7.1.2";

		container lsp-db-version {
			uses pcep:tlv;
			leaf version {
				type uint64;
				mandatory true;
			}
		}
	}

	grouping lsp-identifiers-tlv {
		description "LSP Identifiers TLV";
		reference "http://tools.ietf.org/html/draft-crabbe-pce-stateful-pce-02#section-7.2.2";
		container lsp-identifiers {
			uses pcep:tlv;
			leaf lsp-id {
				type rsvp:lsp-id;
				mandatory true;
			}

			leaf tunnel-id {
				type rsvp:tunnel-id;
				mandatory true;
			}

			choice address-family {
				case ipv4-case {
					container ipv4 {
						leaf ipv4-tunnel-sender-address {
							type inet:ipv4-address;
							mandatory true;
						}
						leaf ipv4-extended-tunnel-id {
							type rsvp:ipv4-extended-tunnel-id;
							mandatory true;
						}
					}
				}
				case ipv6-case {
					container ipv6 {
						leaf ipv6-tunnel-sender-address {
							type inet:ipv6-address;
							mandatory true;
						}
						leaf ipv6-extended-tunnel-id {
							type rsvp:ipv6-extended-tunnel-id;
							mandatory true;
						}
					}
				}
			}
		}
	}

	grouping lsp-error-code-tlv {
		description "LSP Error Code TLV";
		reference "http://tools.ietf.org/html/draft-crabbe-pce-stateful-pce-02#section-7.2.3";
		container lsp-error-code {
			uses pcep:tlv;
			leaf error-code {
				type uint32;
				mandatory true;
			}
		}
	}

	grouping rsvp-error-spec-tlv {
		description "RSVP Error Spec TLV";
		reference "http://tools.ietf.org/html/draft-crabbe-pce-stateful-pce-02#section-7.2.4";
		container rsvp-error-spec {
			uses pcep:tlv;
			choice error-type {
				case rsvp-case {
					container rsvp-error {
						uses rsvp:error-spec;
					}
				}
				case user-case {
					container user-error {
						uses rsvp:user-error-spec;
					}
				}
			}
		}
	}

	grouping stateful-capability-tlv {
		description "Stateful PCE Capability TLV";
		reference "http://tools.ietf.org/html/draft-crabbe-pce-stateful-pce-02#section-7.1.1";

		container stateful {
			uses pcep:tlv;

			leaf lsp-update-capability {
				type boolean;
				default false;
			}
			leaf include-db-version {
				type boolean;
				default false;
			}
		}
	}

	grouping symbolic-path-name-tlv {
		description "Symbolic Path Name TLV";
		reference "http://tools.ietf.org/html/draft-crabbe-pce-stateful-pce-02#section-7.2.1";
		container symbolic-path-name {
			uses pcep:tlv;
			leaf path-name {
				type symbolic-path-name;
				mandatory true;
			}
		}
	}

	grouping lsp-object {
		description "LSP Object";
		reference "http://tools.ietf.org/html/draft-crabbe-pce-stateful-pce-02#section-7.2";

		container lsp {
			uses pcep:object;
			container "tlvs" {
				uses lsp-db-version-tlv;

				uses lsp-error-code-tlv;

				uses lsp-identifiers-tlv;

				uses rsvp-error-spec-tlv;

				uses symbolic-path-name-tlv;
			}

			leaf plsp-id {
				type plsp-id;
				mandatory true;
			}

			leaf delegate {
				type boolean;
				default false;
			}

			leaf sync {
				type boolean;
				default false;
			}

			leaf remove {
				type boolean;
				default false;
			}

			leaf operational {
				type boolean;
				default false;
			}
		}
	}

	grouping pcupd-message {
		uses pcep:message;

		container pcupd-message {
			description "State Update Request Message";
			reference "http://tools.ietf.org/html/draft-crabbe-pce-stateful-pce-02#section-6.2";

			uses pcep:message-header;

			list updates {
				uses lsp-object;

				container path {
					uses pcep:path-definition;
				}
			}
		}
	}

	grouping pcrpt-message {
		uses pcep:message;

		container pcrpt-message {
			description "State Report Message";
			reference "http://tools.ietf.org/html/draft-crabbe-pce-stateful-pce-02#section-6.1";

			uses pcep:message-header;

			list reports {
				uses lsp-object;

				container path {
					uses pcep:path-definition;
				}
			}
		}
	}

	notification pcupd {
		uses pcupd-message;
	}

	notification pcrpt {
		uses pcrpt-message;
	}

	augment "/msg:open/msg:open-message/msg:open/msg:tlvs" {
		uses stateful-capability-tlv;

		uses lsp-db-version-tlv;
	}

	augment "/msg:pcerr/msg:pcerr-message/msg:error-type/msg:session-case/msg:session/msg:open/msg:tlvs" {
		uses stateful-capability-tlv;

		uses lsp-db-version-tlv;
	}

	augment "/msg:pcreq/msg:pcreq-message/msg:requests/msg:segment-computation/msg:p2p" {
		uses lsp-object;
	}

	augment "/msg:pcrep/msg:pcrep-message/msg:replies" {
		uses lsp-object;
	}
}
