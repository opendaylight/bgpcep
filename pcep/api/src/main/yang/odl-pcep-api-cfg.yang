// vi: set smarttab et sw=4 tabstop=4:
module odl-pcep-api-cfg {
    yang-version 1;
    namespace "urn:opendaylight:params:xml:ns:yang:controller:pcep";
    prefix "pcep";

    import config { prefix config; revision-date 2013-04-05; }

    organization "Cisco Systems, Inc.";

    contact "Robert Varga <rovarga@cisco.com>";

    description
        "This module contains the base YANG definitions for
         PCEP protocol handler.

        Copyright (c)2013 Cisco Systems, Inc. All rights reserved.;

        This program and the accompanying materials are made available
        under the terms of the Eclipse Public License v1.0 which
        accompanies this distribution, and is available at
        http://www.eclipse.org/legal/epl-v10.html";

    revision "2013-04-09" {
        description
            "Initial revision";
    }

    identity pcep-dispatcher {
        description
            "Service representing a PCEP dispatcher service. The service
             can create both PCEP client sessions and PCEP servers.";

        base "config:service-type";
        config:java-class "org.opendaylight.protocol.pcep.PCEPDispatcher";
    }

    identity pcep-session-proposal-factory {
        description
            "Service representing a PCEP session proposal factory service. The service
             provides initial session attributes given by the user.";

        base "config:service-type";
        config:java-class "org.opendaylight.protocol.pcep.PCEPSessionProposalFactory";
        config:disable-osgi-service-registration;
    }

    identity pcep-capability {
        description "Service for storing usability of specific capabilities during
            opened PCEP session.";
        base "config:service-type";
        config:java-class "org.opendaylight.protocol.pcep.PCEPCapability";
    }
}
