module topology-tunnel-sr {
	yang-version 1;
	namespace "urn:opendaylight:params:xml:ns:yang:topology:tunnel:sr";
	prefix "tun-sr";

	import network-topology-sr { prefix sr; revision-date 2013-08-19; }
	import network-topology { prefix nt; revision-date 2013-07-12; }
	import topology-tunnel { prefix tt; revision-date 2013-08-19; }
	import topology-tunnel-p2p { prefix p2p; revision-date 2013-08-19; }

	organization "Cisco Systems, Inc.";
	contact "Robert Varga <rovarga@cisco.com>";

	description
		"This module contains the Segment Routing extensions to
		base tunnel topology model.

		Copyright (c)2013 Cisco Systems, Inc. All rights reserved.

		This program and the accompanying materials are made available
		under the terms of the Eclipse Public License v1.0 which
		accompanies this distribution, and is available at
		http://www.eclipse.org/legal/epl-v10.html";

	revision "2013-08-19" {
		description
			"Initial revision.";
		reference "";
	}

	grouping tunnel-sr-type {
		container sr-tunnel {
			presence "indicates a link is a Segment Routed tunnel";
		}
	}

	grouping tunnel-sr-path-p2p-hop-attributes {
		leaf segment-id {
			type sr:segment-id;
		}
	}

	augment "/nt:network-topology/nt:topology/tt:paths/tt:path-types" {
		uses tunnel-sr-type;
	}

	augment "/nt:network-topology/nt:topology/tt:paths/p2p:explicit-hops" {
		when "../../tunnel-types/sr-tunnel";
		uses tunnel-sr-path-p2p-hop-attributes;
	}

	augment "/nt:network-topology/nt:topology/tt:paths/p2p:reported-hops" {
		when "../../path-types/sr-tunnel";
		uses tunnel-sr-path-p2p-hop-attributes;
	}
}
