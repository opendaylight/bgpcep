module pcep-service {
	yang-version 1;
	namespace "urn:opendaylight:params:xml:ns:yang:pcep-service";
	prefix "pcep-svc";

	import pcep-types { prefix pcep; revision-date 2013-10-05; }
	import ietf-inet-types { prefix inet; revision-date 2010-09-24; }

	organization "Cisco Systems, Inc.";
	contact "Robert Varga <rovarga@cisco.com>";

	description
		"This module contains the base data model of a PCEP message.
		It rolls up the definitions contained in RFC5440, RFC5520
		and RFC6006.

		Copyright (c)2013 Cisco Systems, Inc. All rights reserved.

		This program and the accompanying materials are made available
		under the terms of the Eclipse Public License v1.0 which
		accompanies this distribution, and is available at
		http://www.eclipse.org/legal/epl-v10.html";

	revision "2013-10-05" {
		description
			"Initial revision.";
	}

	container pcep {
		list servers {
			leaf address {
				type inet:ip-address;
				mandatory true;
			}
			leaf port {
				type uint16 {
					range 1..65535;
				}
				default 4189;
			}

			// FIXME: finish this
		}

		list client-sessions {
			leaf address {
				type inet:ip-address;
				mandatory true;
			}
			leaf port {
				type uint16 {
					range 1..65535;
				}
				default 4189;
			}

			// FIXME: finish this
		}

		list server-sessions {
			// FIXME: finish this
		}
	}

	notification open {
		uses pcep:open-message;
	}

	notification keepalive {
		uses pcep:keepalive-message;
	}

	notification pcreq {
		uses pcep:pcreq-message;
	}

	notification pcrep {
		uses pcep:pcrep-message;
	}

	notification pcntf {
		uses pcep:pcntf-message;
	}

	notification pcerr {
		uses pcep:pcerr-message;
	}

	notification close {
		uses pcep:close-message;
	}

	notification pcupd {
		uses pcep:pcupd-message;
	}

	notification pcrpt {
		uses pcep:pcrpt-message;
	}

	notification pcinitiate {
		uses pcep:pcinitiate-message;
	}

	rpc send-message {
		input {
			choice message {
				case close-message {
					uses pcep:close-message;
				}
				case keepalive-message {
					uses pcep:keepalive-message;
				}
				case open-message {
					uses pcep:open-message;
				}
				case pcerr-message {
					uses pcep:pcerr-message;
				}
				case pcinitiate-message {
					uses pcep:pcinitiate-message;
				}
				case pcrep-message {
					uses pcep:pcrep-message;
				}
				case pcreq-message {
					uses pcep:pcreq-message;
				}
				case pcrpt-message {
					uses pcep:pcrpt-message;
				}
				case pcupd-message {
					uses pcep:pcupd-message;
				}
			}
		}
	}
}
