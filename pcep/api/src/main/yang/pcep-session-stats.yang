// vi: set smarttab et sw=4 tabstop=4:
module pcep-session-stats {
    yang-version 1;
    namespace "urn:opendaylight:params:xml:ns:yang:controller:pcep:stats";
    prefix "pcep-stats";

    organization "Cisco Systems, Inc.";

    contact "Milos Fabian <milfabia@cisco.com>";

    description
        "This module contains the base YANG definitions for
         PCEP session statistics.

        Copyright (c)2014 Cisco Systems, Inc. All rights reserved.;

        This program and the accompanying materials are made available
        under the terms of the Eclipse Public License v1.0 which
        accompanies this distribution, and is available at
        http://www.eclipse.org/legal/epl-v10.html";

    revision "2017-11-13" {
        description
            "Initial revision";
    }

    revision "2014-10-06" {
        description
            "Initial revision";
    }

    grouping error {
        description "PCEP Error-type/value.";
        leaf error-type {
            type uint8;
            default 0;
        }
        leaf error-value {
            type uint8;
            default 0;
        }
    }

    grouping preferences {
        leaf keepalive {
            description "Advertised keep-alive value.";
            type uint8;
            default 0;
        }

        leaf deadtimer {
            description "Advertised deadtimer value.";
            type uint8;
            default 0;
        }

        leaf ip-address {
            description "Peer's IP address.";
            type string;
            default "";
        }

        leaf session-id {
            description "Peer's session identifier.";
            type uint16;
            default 0;
        }
    }

    grouping error-messages-grouping {
        container error-messages {
            description "The message statistics of received/sent PCErr messages.";
            leaf received-error-msg-count {
                description "Total number of received PCErr messages.";
                type uint32;
                default 0;
            }

            leaf sent-error-msg-count {
                description "Total number of sent PCErr messages.";
                type uint32;
                default 0;
            }

            container last-received-error {
                description "Type/value tuple of last received error.";
                uses error;
            }

            container last-sent-error {
                description "Type/value tuple of last sent error.";
                uses error;
            }
        }
    }

    grouping reply-time-grouping {
        container reply-time {
            description "Measures time elapsed from request's send to reply's received.";

            leaf average-time {
                description "Average time (in milliseconds) of gauged values.";
                type uint32;
                default 0;
            }

            leaf min-time {
                description "Minimal measured time value (in milliseconds).";
                type uint32;
                default 0;
            }

            leaf max-time {
                description "Maximal measured time value (in milliseconds).";
                type uint32;
                default 0;
            }
        }
    }

    grouping pcep-session-state {
        description "PCEP session statistics.";

        leaf session-duration {
            description "Elapsed time (in d:H:m:s) from session-up until now.";
            type string;
        }

        leaf synchronized {
            description "Represents synchronization status.";
            type boolean;
            default false;
        }

        container peer-capabilities {
            description "Remote peer's (PCC) advertised capabilities.";
        }

        container messages {
            description "The statistics of PCEP received/sent messages from the PCE point of view.";

            uses reply-time-grouping;

            leaf received-msg-count {
                description "Total number of received PCEP messages.";
                type uint32;
                default 0;
            }

            leaf sent-msg-count {
                description "Total number of sent PCEP messages.";
                type uint32;
                default 0;
            }

            leaf last-sent-msg-timestamp {
                description "The timestamp of last sent message.";
                type uint32;
                default 0;
            }

            leaf unknown-msg-received {
                description "The number of received unknown messages.";
                type uint16;
                default 0;
            }

            uses error-messages-grouping;
        }

        container local-pref {
            description "The local (PCE) preferences.";
            uses preferences;
        }

        container peer-pref {
            description "The remote peer (PCC) preferences.";
            uses preferences;
        }


        leaf delegated-lsps-count {
            description "The number of delegated LSPs (tunnels) from PCC.";
            type uint16;
            default 0;
        }
    }

    grouping pcep-session-state-grouping {
        container pcep-session-state {
            uses pcep-session-state;
        }
    }
}
