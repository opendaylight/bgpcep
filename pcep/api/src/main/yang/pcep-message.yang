module pcep-message {
    yang-version 1;
    namespace "urn:opendaylight:params:xml:ns:yang:pcep:message";
    prefix "pcep-msg";

    import pcep-types { prefix pcep; revision-date 2025-06-02; }

    organization "Cisco Systems, Inc.";
    contact "Robert Varga <rovarga@cisco.com>";

    description
        "This module contains the base data model of a PCEP message.
        It rolls up the definitions contained in RFC5440, RFC5520
        and RFC6006, RFC5886.

        Copyright (c)2013 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision "2013-10-07" {
        description
            "Initial revision.";
    }

    notification open {
        uses pcep:open-message;
    }

    notification keepalive {
        uses pcep:keepalive-message;
    }

    notification pcreq {
        uses pcep:pcreq-message;
    }

    notification pcrep {
        uses pcep:pcrep-message;
    }

    notification pcntf {
        uses pcep:pcntf-message;
    }

    notification pcerr {
        uses pcep:pcerr-message;
    }

    notification close {
        uses pcep:close-message;
    }

    notification starttls {
        uses pcep:start-tls-message;
    }

    notification pcmonreq {
        uses pcep:pcreq-message;
    }

    notification pcmonrep {
        uses pcep:pcmonrep-message;
    }
}
