module odl-pcep-message {
    yang-version 1;
    namespace "urn:opendaylight:params:xml:ns:yang:pcep:message";
    prefix "pcep-msg";

    import odl-pcep-types { prefix pcep-types; revision-date 2025-09-30; }
    import odl-pcep-object { prefix pcep-object; revision-date 2025-09-30; }

    organization "Orange";
    contact "Olivier Dugeon <olivier.dugeon@orange.com>";

    description
        "This module contains the base data model of a PCEP message.
        It rolls up the definitions contained in RFC5440, RFC5520
        and RFC6006, RFC5886.

        Copyright (c)2025 Orange. All rights reserved.

        This program and the accompanying materials are made available
        under the terms of the Eclipse Public License v1.0 which
        accompanies this distribution, and is available at
        http://www.eclipse.org/legal/epl-v10.html";

    revision "2025-09-30" {
        description "Split old pcep-types into odl-pcep-types, odl-pcep-object and
                     odl-pcep-message following the redesign of pcep yang models.
                     This is the Message part.";
    }

    revision "2018-11-09" {
        description
            "P2MP extension.";
        reference "RFC8306";
    }

    revision "2013-10-07" {
        description
            "Initial revision.";
    }

    // Messages

    grouping message {
        description "Marker grouping for message groupings.";
    }

    grouping message-header {
        description "Common Header";
        reference "https://tools.ietf.org/html/rfc5440#section-6.1";

        leaf version {
            type pcep-types:protocol-version;
            default 1;
        }
    }

    grouping open-message {
        uses message;

        container open-message {
            description "Open Message";
            reference "https://tools.ietf.org/html/rfc5440#section-6.2";

            uses message-header;

            uses pcep-object:open-object;
        }
    }

    grouping keepalive-message {
        uses message;

        container keepalive-message {
            description "Keepalive Message";
            reference "https://tools.ietf.org/html/rfc5440#section-6.3";

            uses message-header;
        }
    }

    grouping pcreq-message {
        uses message;

        container pcreq-message {
            description "Path Computation Request Message";
            reference "https://tools.ietf.org/html/rfc5440#section-6.4";

            uses message-header;

            list requests {
                uses pcep-object:rp-object;

                container path-key-expansion {
                    when "rp/path-key = true";
                    uses pcep-object:path-key-object;
                }

                container segment-computation {
                    when "rp/path-key = false";

                    container p2p {
                        when "../rp/p2mp = false";
                        uses pcep-object:p2p;
                    }

                    container p2mp {
                        reference "https://tools.ietf.org/html/rfc8306#section-3.4";
                        when "../rp/p2mp = true";

                        uses pcep-object:p2mp;
                    }
                }

                uses pcep-object:vendor-information-objects;
            }

            list svec {
                uses pcep-object:svec;
            }

            container monitoring-request {
                uses pcep-object:monitoring;

                list pce-id-list {
                    uses pcep-object:pce-id-object;
                }
            }
        }
    }

    grouping pcmonrep-message {
        description "The PCMonRep message is used to provide PCE
        state metrics back to the requester for out-of-band monitoring requests.";
        reference "https://tools.ietf.org/html/rfc5886#section-9.2";

        uses message;
        container pcmonrep-message {
            uses pcep-object:monitoring-response;
        }
    }

    grouping pcrep-message {
        uses message;

        container pcrep-message {
            description "Path Computation Reply Message";
            reference "https://tools.ietf.org/html/rfc5440#section-6.5";

            uses message-header;

            list replies {
                uses pcep-object:replies;
            }
        }
    }

    grouping pcntf-message {
        uses message;

        container pcntf-message {
            description "Notification Message";
            reference "https://tools.ietf.org/html/rfc5440#section-6.6";

            uses message-header;

            list notifications {
                list rps {
                    uses pcep-object:rp-object;
                }

                list notifications {
                    uses pcep-object:notification-object;
                }
            }
        }
    }

    grouping pcerr-message {
        uses message;

        container pcerr-message {
            description "Error Message";
            reference "https://tools.ietf.org/html/rfc5440#section-6.7";

            uses message-header;

            list errors {
                uses pcep-object:pcep-error-object;
            }

            choice error-type {
                case request-case {
                    container request {
                        list rps {
                            uses pcep-object:rp-object;
                        }
                    }
                }

                case session-case {
                    container session {
                        uses pcep-object:open-object;
                    }
                }
            }
        }
    }

    grouping close-message {
        uses message;

        container c-close-message {
            description "Close Message";
            reference "https://tools.ietf.org/html/rfc5440#section-6.8";

            uses message-header;

            uses pcep-object:close-object;
        }
    }

    grouping start-tls-message {
        uses message;

        container start-tls-message {
            description "StartTLS Message";
            reference "https://tools.ietf.org/html/draft-ietf-pce-pceps-02#section-3.3";

            uses message-header;
        }
    }

    notification open {
        uses open-message;
    }

    notification keepalive {
        uses keepalive-message;
    }

    notification pcreq {
        uses pcreq-message;
    }

    notification pcrep {
        uses pcrep-message;
    }

    notification pcntf {
        uses pcntf-message;
    }

    notification pcerr {
        uses pcerr-message;
    }

    notification close {
        uses close-message;
    }

    notification starttls {
        uses start-tls-message;
    }

    notification pcmonreq {
        uses pcreq-message;
    }

    notification pcmonrep {
        uses pcmonrep-message;
    }
}
