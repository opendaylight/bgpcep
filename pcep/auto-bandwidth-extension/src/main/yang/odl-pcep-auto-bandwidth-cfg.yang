module odl-pcep-auto-bandwidth-cfg {
    yang-version 1;
    namespace "urn:opendaylight:params:xml:ns:yang:controller:pcep:auto:bandwidth:cfg";
    prefix "auto-bw-cfg";

    import config { prefix config; revision-date 2013-04-05; }
    import odl-pcep-api-cfg { prefix pcep; revision-date 2013-04-09; }
    import odl-pcep-spi-cfg { prefix spi; revision-date 2013-11-15; }

    organization "Cisco Systems, Inc.";

    contact "Milos Fabian <milfabia@cisco.com>";

    description
        "This module contains the base YANG definitions for
         draft-ietf-pce-stateful-pce-07 extensions configuration.

        Copyright (c)2016 Cisco Systems, Inc. All rights reserved.;

        This program and the accompanying materials are made available
        under the terms of the Eclipse Public License v1.0 which
        accompanies this distribution, and is available at
        http://www.eclipse.org/legal/epl-v10.html";

    revision 2016-01-09 {
        description "Initial revision";
    }

    identity pcep-parser-auto-bandwidth {
        base config:module-type;
        config:provided-service spi:extension;
        config:java-name-prefix AutoBandwidthPCEPParser;
    }

    augment "/config:modules/config:module/config:configuration" {
        case pcep-parser-auto-bandwidth {
            when "/config:modules/config:module/config:type = 'pcep-parser-auto-bandwidth'";
            leaf bandwidth-usage-object-type {
                type uint8 {
                    range 3..15;
                }
                default 5;
            }
        }
    }

}
