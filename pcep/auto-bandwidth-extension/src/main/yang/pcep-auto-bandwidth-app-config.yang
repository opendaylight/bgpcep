module pcep-auto-bandwidth-app-config {
    yang-version 1;
    namespace "urn:opendaylight:params:xml:ns:yang:controller:pcep:auto-bandwidth-app-config";
    prefix "pcep-auto-bandwidth-app-config";

    description
      "Configuration for the PCEP auto bandwidth extension.";

    revision "2016-07-07" {
        description
            "Initial revision.";
    }

    container pcep-auto-bandwidth-app-config {
        leaf bandwidth-usage-object-type {
            type uint16 {
                range "3..15";
            }

            default 5;
        }
    }
}
