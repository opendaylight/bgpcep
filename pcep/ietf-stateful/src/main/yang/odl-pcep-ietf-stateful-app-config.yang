module pcep-ietf-stateful-app-config {
    yang-version 1;
    namespace "urn:opendaylight:params:xml:ns:yang:controller:pcep:ietf-stateful-app-config";
    prefix "pcep-ietf-stateful-app-config";

    description
      "Configuration for the PCEP IETF stateful extension.";

    revision "2016-07-07" {
        description
            "Initial revision.

            Copyright (c) 2016 Brocade Communications Systems, Inc. All rights reserved.

            This program and the accompanying materials are made available
            under the terms of the Eclipse Public License v1.0 which
            accompanies this distribution, and is available at
            http://www.eclipse.org/legal/epl-v10.html";
    }

    grouping stateful-capabilities {
        leaf initiated {
            type boolean;
            default true;
        }

        leaf stateful {
            type boolean;
            default true;
        }

        leaf active {
            type boolean;
            default true;
        }

        leaf triggered-initial-sync {
            type boolean;
            default true;
        }

        leaf delta-lsp-sync-capability {
            type boolean;
            default true;
        }

        leaf triggered-resync {
            type boolean;
            default true;
        }

        leaf include-db-version {
            type boolean;
            default true;
        }
    }

    container pcep-ietf-stateful-config {
        uses stateful-capabilities;
    }
}
