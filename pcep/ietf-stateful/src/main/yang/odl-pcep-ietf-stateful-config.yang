module odl-pcep-ietf-stateful-config {
    namespace "urn:opendaylight:params:xml:ns:yang:pcep:ietf-stateful-config";
    prefix "opisc";

    description
      "Configuration for the PCEP IETF stateful extension.

       Copyright (c) 2016 Brocade Communications Systems, Inc. All rights reserved.
       Copyright (c) 2023 PANTHEON.tech, s.r.o.

       This program and the accompanying materials are made available
       under the terms of the Eclipse Public License v1.0 which
       accompanies this distribution, and is available at
       http://www.eclipse.org/legal/epl-v10.html";

    revision "2023-01-15" {
        description "Revision of pcep-ietf-stateful-app-config without datastore anchor";
    }

    grouping stateful-capabilities {
        leaf initiated {
            type boolean;
            default true;
        }

        leaf stateful {
            type boolean;
            default true;
        }

        leaf active {
            type boolean;
            default true;
        }

        leaf triggered-initial-sync {
            type boolean;
            default true;
        }

        leaf delta-lsp-sync-capability {
            type boolean;
            default true;
        }

        leaf triggered-resync {
            type boolean;
            default true;
        }

        leaf include-db-version {
            type boolean;
            default true;
        }
    }
}
