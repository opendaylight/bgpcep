module odl-pcep-ietf-initiated00 {
    yang-version 1;
    namespace "urn:opendaylight:params:xml:ns:yang:pcep:crabbe:initiated";
    prefix "crabbe";

    import pcep-types { prefix pcep; revision-date 2018-11-09; }
    import pcep-message { prefix msg; revision-date 2018-11-09; }
    import network-topology { prefix nt; revision-date 2013-10-21; }
    import network-topology-pcep { prefix topo; revision-date 2020-01-20; }
    import odl-pcep-ietf-stateful07 { prefix stateful; revision-date 2018-11-09; }

    organization "Cisco Systems, Inc.";
    contact "Robert Varga <rovarga@cisco.com>";

    description
        "This module contains the data model of PCEP extensions defined
        in draft-ietf-pce-pce-initiated-lsp.

        Copyright (c)2013 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision 2017-10-25 {
        description "Update network-topology-pcep revision";
    }

    revision "2013-11-26" {
        description
            "Initial revision.";
        reference "http://tools.ietf.org/html/draft-ietf-pce-pce-initiated-lsp-00";
    }

    grouping pcinitiate-message {
        uses pcep:message;

        container pcinitiate-message {
            description "LSP Initiate Message";
            reference "http://tools.ietf.org/html/draft-ietf-pce-pce-initiated-lsp-00#section-5.1";

            uses pcep:message-header;

            list requests {
                uses stateful:srp-object;

                uses stateful:lsp-object;

                uses pcep:endpoints-object;

                uses pcep:explicit-route-object;

                uses pcep:lsp-attributes;
            }
        }
    }

    grouping initiated-capability-tlv {
        reference "http://tools.ietf.org/html/draft-ietf-pce-pce-initiated-lsp-00#section-4.1";
        leaf initiation {
            type boolean;
            default false;
        }
    }

    augment "/stateful:pcupd/stateful:pcupd-message/stateful:updates/stateful:srp" {
        reference "http://tools.ietf.org/html/draft-ietf-pce-pce-initiated-lsp-00#section-5.2";
        leaf remove {
            type boolean;
            default false;
        }
    }

    augment "/stateful:pcrpt/stateful:pcrpt-message/stateful:reports/stateful:srp" {
        reference "http://tools.ietf.org/html/draft-ietf-pce-pce-initiated-lsp-00#section-5.2";
        leaf remove {
            type boolean;
            default false;
        }
    }

    augment "/stateful:pcupd/stateful:pcupd-message/stateful:updates/stateful:lsp" {
        reference "http://tools.ietf.org/html/draft-ietf-pce-pce-initiated-lsp-00#section-5.3.1";
        leaf create {
            type boolean;
            default false;
        }
    }

    augment "/stateful:pcrpt/stateful:pcrpt-message/stateful:reports/stateful:lsp" {
        reference "http://tools.ietf.org/html/draft-ietf-pce-pce-initiated-lsp-00#section-5.3.1";
        leaf create {
            type boolean;
            default false;
        }
    }

    augment "/msg:open/msg:open-message/msg:open/msg:tlvs/stateful:stateful" {
        uses initiated-capability-tlv;
    }

    notification pcinitiate {
        uses pcinitiate-message;
    }

    augment "/nt:network-topology/nt:topology/nt:node/topo:path-computation-client/topo:stateful-tlv/stateful:stateful" {
        uses initiated-capability-tlv;
    }

    augment "/nt:network-topology/nt:topology/nt:node/topo:path-computation-client/topo:reported-lsp/topo:path/stateful:lsp" {
        reference "http://tools.ietf.org/html/draft-ietf-pce-pce-initiated-lsp-00#section-5.3.1";
        leaf create {
            type boolean;
            default false;
        }
    }
}
