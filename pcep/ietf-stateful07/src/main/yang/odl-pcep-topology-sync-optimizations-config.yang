// vi: set smarttab et sw=4 tabstop=4:
module odl-pcep-topology-sync-optimizations-config {
    yang-version 1;
    namespace "urn:opendaylight:params:xml:ns:yang:topology:pcep:sync:optimizations:config";
    prefix pnc;

    import network-topology { prefix nt; revision-date 2013-10-21; }
    import network-topology-pcep { prefix pn; revision-date 2017-10-25; }
    import yang-ext { prefix ext; revision-date 2013-07-09; }
    import pcep-config { prefix pc; revision-date 2017-10-25; }
    import odl-pcep-sync-optimizations { prefix opso; revision-date 2017-10-25; }
    import network-pcep-topology-config { prefix nptc; revision-date 2017-10-25; }

    description
        "This module contains the PCEP config extensions to base topology model.
         Copyright (c)2017 AT&T Services, Inc. All rights reserved.;

         This program and the accompanying materials are made available
         under the terms of the Eclipse Public License v1.0 which
         accompanies this distribution, and is available at
         http://www.eclipse.org/legal/epl-v10.html";

    organization "AT&T Services, Inc.";
    contact "Claudio D. Gasparini <claudio.gasparini@pantheon.sk>";

    revision "2017-10-25" {
        description
            "Initial revision.";
    }

    augment "/nt:network-topology/nt:topology/nt:node/nptc:session-config" {
        when "../nt:topology-types/pn:topology-pcep";
        ext:augment-identifier pcep-node-sync-config;
        description "Augment Pcep topology node with synchronization config";

        uses opso:speaker-entity-id;
    }
}
