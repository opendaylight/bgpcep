module odl-pcep-sync-optimizations {
    yang-version 1;
    namespace "urn:opendaylight:params:xml:ns:yang:controller:pcep:sync:optimizations";
    prefix "sync-optimizations";

    import pcep-types { prefix pcep; revision-date 2018-11-09; }
    import pcep-message { prefix msg; revision-date 2018-11-09; }
    import network-topology { prefix nt; revision-date 2013-10-21; }
    import network-topology-pcep { prefix topo; revision-date 2020-01-20; }
    import odl-pcep-ietf-stateful07 { prefix stateful; revision-date 2018-11-09; }

    organization "Pantheon Technologies";
    contact "Iveta Halanova <iveta.halanova@pantheon.sk>";

    description
        "This module contains the data model of PCEP extensions defined
        in draft-ietf-pce-stateful-sync-optimizations-02.

        Copyright (c)2015 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision 2017-10-25 {
        description "Update network-topology-pcep revision";
    }

    revision "2015-07-14" {
        description
            "Initial revision.";
        reference "https://tools.ietf.org/html/draft-ietf-pce-stateful-sync-optimizations-02";
    }

    grouping sync-optimizations-capability-tlv {
        reference "http://tools.ietf.org/html/draft-ietf-pce-pce-initiated-lsp-00#section-4.1";
        leaf triggered-initial-sync {
            type boolean;
            default false;
        }
        leaf delta-lsp-sync-capability {
            type boolean;
            default false;
        }
        leaf triggered-resync {
            type boolean;
            default false;
        }
        leaf include-db-version {
            type boolean;
            default false;
        }
    }

    grouping lsp-db-version-tlv {
        container lsp-db-version {
            uses pcep:tlv;
            leaf lsp-db-version-value {
                type uint64;
            }
        }
    }

    grouping speaker-entity-id {
        leaf speaker-entity-id-value {
            type binary;
        }
    }

    grouping speaker-entity-id-tlv {
        container speaker-entity-id {
            uses pcep:tlv;
            uses speaker-entity-id;
        }
    }

    augment "/msg:open/msg:open-message/msg:open/msg:tlvs/stateful:stateful" {
        uses sync-optimizations-capability-tlv;
    }

    augment "/nt:network-topology/nt:topology/nt:node/topo:path-computation-client/topo:stateful-tlv/stateful:stateful" {
        uses sync-optimizations-capability-tlv;
    }

    augment "/msg:open/msg:open-message/msg:open/msg:tlvs" {
        uses lsp-db-version-tlv;
        uses speaker-entity-id-tlv;
    }

    augment "/stateful:pcupd/stateful:pcupd-message/stateful:updates/stateful:lsp/stateful:tlvs" {
        uses lsp-db-version-tlv;
    }

    augment "/stateful:pcrpt/stateful:pcrpt-message/stateful:reports/stateful:lsp/stateful:tlvs" {
        uses lsp-db-version-tlv;
    }

    augment "/nt:network-topology/nt:topology/nt:node/topo:path-computation-client/topo:reported-lsp/topo:path/stateful:lsp/stateful:tlvs" {
        uses lsp-db-version-tlv;
    }

    augment "/topo:add-lsp/topo:input/topo:arguments/stateful:lsp/stateful:tlvs" {
        uses lsp-db-version-tlv;
    }

    augment "/topo:update-lsp/topo:input/topo:arguments/stateful:lsp/stateful:tlvs" {
        uses lsp-db-version-tlv;
    }

    augment "/msg:pcerr/msg:pcerr-message/msg:error-type/msg:session-case/msg:session/msg:open/msg:tlvs" {
        uses lsp-db-version-tlv;
        uses speaker-entity-id-tlv;
    }

    augment "/nt:network-topology/nt:topology/nt:node/topo:path-computation-client" {
        uses lsp-db-version-tlv;
    }
}
