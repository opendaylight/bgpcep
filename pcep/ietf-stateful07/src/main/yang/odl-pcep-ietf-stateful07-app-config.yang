module pcep-ietf-stateful07-app-config {
    yang-version 1;
    namespace "urn:opendaylight:params:xml:ns:yang:controller:pcep:ietf-stateful07-app-config";
    prefix "pcep-ietf-stateful07-app-config";

    description
      "Configuration for the PCEP IETF stateful07 extension.";

    revision "2016-07-07" {
        description
            "Initial revision.";
    }

    grouping stateful-capabilities {
        leaf initiated {
            type boolean;
            default true;
        }

        leaf stateful {
            type boolean;
            default true;
        }

        leaf active {
            type boolean;
            default true;
        }

        leaf triggered-initial-sync {
            type boolean;
            default true;
        }

        leaf delta-lsp-sync-capability {
            type boolean;
            default true;
        }

        leaf triggered-resync {
            type boolean;
            default true;
        }

        leaf include-db-version {
            type boolean;
            default true;
        }
    }

    container pcep-ietf-stateful07-config {
        uses stateful-capabilities;
    }
}
