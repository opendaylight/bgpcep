// vi: set smarttab et sw=4 tabstop=4:
module odl-pcep-ietf-stateful07-cfg {
    yang-version 1;
    namespace "urn:opendaylight:params:xml:ns:yang:controller:pcep:stateful07:cfg";
    prefix "pcep-stateful07";

    import config { prefix config; revision-date 2013-04-05; }
    import odl-pcep-api-cfg { prefix pcep; revision-date 2013-04-09; }
    import odl-pcep-spi-cfg { prefix spi; revision-date 2013-11-15; }

    organization "Cisco Systems, Inc.";

    contact "Robert Varga <rovarga@cisco.com>";

    description
        "This module contains the base YANG definitions for
         draft-ietf-pce-stateful-pce-07 extensions.

        Copyright (c)2013 Cisco Systems, Inc. All rights reserved.;

        This program and the accompanying materials are made available
        under the terms of the Eclipse Public License v1.0 which
        accompanies this distribution, and is available at
        http://www.eclipse.org/legal/epl-v10.html";

    revision "2015-07-14" {
        description
            "Extended stateful capabilities.";
    }

    revision "2014-02-21" {
        description
            "Updated revision dates for imports.";
    }

    identity stateful-capability {
        base config:module-type;
        config:java-name-prefix "PCEPStatefulCapability";
        config:provided-service pcep:pcep-capability;
    }

    grouping stateful-capabilities {
        leaf dead-timer-value {
            type uint8;
            default 120;
        }

        leaf keep-alive-timer-value {
            type uint8;
            default 30;
        }

        leaf initiated {
            type boolean;
            default true;
        }

        leaf stateful {
            type boolean;
            default true;
        }

        leaf active {
            type boolean;
            default true;
        }

        leaf triggered-initial-sync {
            type boolean;
            default true;
        }

        leaf delta-lsp-sync-capability {
            type boolean;
            default true;
        }

        leaf triggered-resync {
            type boolean;
            default true;
        }

        leaf include-db-version {
            type boolean;
            default true;
        }
    }

    augment "/config:modules/config:module/config:configuration" {
        case stateful-capability {
            when "/config:modules/config:module/config:type = 'stateful-capability'";
            uses stateful-capabilities;
        }
    }
}
