// vi: set smarttab et sw=4 tabstop=4:
module config-pcep-topology-provider {
    yang-version 1;
    namespace "urn:opendaylight:params:xml:ns:yang:controller:pcep:topology:provider";
    prefix "p2p";

    import config { prefix config; revision-date 2013-04-05; }
    import odl-programming-spi-cfg { prefix pgmspi; revision-date 2013-11-15; }
    import odl-topology-api-cfg { prefix topo; revision-date 2013-11-15; }
    import ietf-inet-types { prefix inet; revision-date 2010-09-24; }
    import network-topology { prefix nt; revision-date 2013-10-21; }
    import pcep { prefix pcep; revision-date 2013-04-09; }
    import opendaylight-md-sal-binding { prefix mdsal; revision-date 2013-10-28; }
    import odl-tcpmd5-cfg { prefix tcpmd5; revision-date 2014-04-27; }

    organization "Cisco Systems, Inc.";

    contact "Robert Varga <rovarga@cisco.com>";

    description
        "This module contains the base YANG definitions for
        PCEP topology provider service.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity pcep-topology-stateful {
        description
            "Service representing a stateful draft support module";

        base "config:service-type";
        config:java-class "org.opendaylight.bgpcep.pcep.topology.provider.TopologySessionListenerFactory";
    }

    identity pcep-topology-stateful02 {
        base config:module-type;
        config:provided-service pcep-topology-stateful;
        config:java-name-prefix Stateful02TopologySessionListener;
    }

    augment "/config:modules/config:module/config:configuration" {
        case pcep-topology-stateful02 {
            when "/config:modules/config:module/config:type = 'pcep-topology-stateful02'";
        }
    }

    identity pcep-topology-stateful07 {
        base config:module-type;
        config:provided-service pcep-topology-stateful;
        config:java-name-prefix Stateful07TopologySessionListener;
    }

    augment "/config:modules/config:module/config:configuration" {
        case pcep-topology-stateful07 {
            when "/config:modules/config:module/config:type = 'pcep-topology-stateful07'";
        }
    }

    identity pcep-topology-reference {
        description
            "Service representing a PCEP-enabled topology.";

        // FIXME: should be a topology-reference, really
        //base "topo:topology-reference";
        base "config:service-type";
        config:java-class "org.opendaylight.bgpcep.topology.TopologyReference";
    }

    identity pcep-topology-provider {
        base config:module-type;
        config:provided-service pcep-topology-reference;
        config:java-name-prefix PCEPTopologyProvider;
    }

    augment "/config:modules/config:module/config:configuration" {
        case pcep-topology-provider {
            when "/config:modules/config:module/config:type = 'pcep-topology-provider'";

            container data-provider {
                uses config:service-ref {
                    refine type {
                        mandatory true;
                        config:required-identity mdsal:binding-data-broker;
                    }
                }
            }

            container rpc-registry {
                uses config:service-ref {
                    refine type {
                        mandatory true;
                        config:required-identity mdsal:binding-rpc-registry;
                    }
                }
            }

            container dispatcher {
                uses config:service-ref {
                    refine type {
                        mandatory true;
                        config:required-identity pcep:pcep-dispatcher;
                    }
                }
            }

            container scheduler {
                uses config:service-ref {
                    refine type {
                        mandatory true;
                        config:required-identity pgmspi:instruction-scheduler;
                    }
                }
            }

            container stateful-plugin {
                uses config:service-ref {
                    refine type {
                        mandatory true;
                        config:required-identity pcep-topology-stateful;
                    }
                }
            }

            leaf topology-id {
                type nt:topology-id;
                mandatory true;
            }

            leaf listen-address {
                type inet:ip-address;
                default "0.0.0.0";
            }

            leaf listen-port {
                type inet:port-number;
                default 4189;
            }

            list client {
                leaf address {
                    type inet:ip-address;
                }
                key "address";

                leaf password {
                    type tcpmd5:rfc2385-key;
                    description "RFC2385 shared secret";
                }
            }
        }
    }
}
