// vi: set smarttab et sw=4 tabstop=4:
module odl-pcep-stats-provider {
    yang-version 1;
    namespace "urn:opendaylight:params:xml:ns:yang:odl:pcep:stats:provider:config";
    prefix pspc;

    import network-topology { prefix nt; revision-date 2013-10-21; }
    import network-topology-pcep { prefix pn; }
    import odl-codegen-extensions { prefix oce; }

    description
        "This module contains the base YANG definitions for
         PCEP Stats Provider Configuration.
         Copyright (c)2017 AT&T Services, Inc. All rights reserved.;

         This program and the accompanying materials are made available
         under the terms of the Eclipse Public License v1.0 which
         accompanies this distribution, and is available at
         http://www.eclipse.org/legal/epl-v10.html";

    revision "2022-07-30" {
        description
            "Integrated with PCEP network topology";
    }

    revision "2017-11-13" {
        description
            "Initial revision.";
    }

    augment "/nt:network-topology/nt:topology/nt:topology-types/pn:topology-pcep" {
        oce:augment-identifier pcep-topology-node-stats-provider-aug;

        leaf timer {
            type uint16 {
                range 1..max;
            }
            default 5;
            units "seconds";
        }
    }
}
