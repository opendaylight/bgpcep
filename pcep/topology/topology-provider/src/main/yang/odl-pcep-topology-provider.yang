module odl-pcep-topology-provider {
    namespace "urn:opendaylight:params:xml:ns:yang:odl:pcep:topology-provider";
    prefix optp;

    import network-topology { prefix nt; }
    import network-topology-pcep { prefix pn; }
    import odl-pcep-config { prefix pc; }

    description
        "This module contains the base YANG definitions for configuring
         the PCEP Topology provider.

         Copyright (c)2023 PANTHEON.tech, s.r.o. and others.  All rights reserved.

         This program and the accompanying materials are made available
         under the terms of the Eclipse Public License v1.0 which
         accompanies this distribution, and is available at
         http://www.eclipse.org/legal/epl-v10.html";

    revision "2023-01-15" {
        description "Initial revision";
    }

    augment "/nt:network-topology/nt:topology/nt:topology-types/pn:topology-pcep" {
        container capabilities {
            container association-group {
                leaf enabled {
                    type boolean;
                    default true;
                }
                uses pc:association-capabilities;
            }
            container stateful {
                leaf enabled {
                    type boolean;
                    default true;
                }

                uses pc:stateful-capabilities;
            }
            container path-setup-type {
                leaf enabled {
                    type boolean;
                    default true;
                }
                uses pc:path-setup-type-capabilities;
            }
            container p2mp {
                leaf enabled {
                    type boolean;
                    default true;
                }
            }
            container auto-bandwidth {
                leaf enabled {
                    type boolean;
                    default false;
                }
            }
        }
    }
}
