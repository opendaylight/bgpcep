module network-topology-pcep-programming {
    // vi: set et smarttab sw=4 tabstop=4:
    yang-version 1;
    namespace "urn:opendaylight:params:xml:ns:yang:topology:pcep:programming";
    prefix "pnp";

    import network-topology-programming { prefix ntp; revision-date 2013-11-02; }
    import network-topology-pcep { prefix pcep; }

    organization "Cisco Systems, Inc.";
    contact "Robert Varga <rovarga@cisco.com>";

    description
        "This module contains the PCEP extensions to base topology model. It
        exposes the LSPs for which a particular node is the head end.

        This module exposes three programming instructions,add-lsp,
        remove-lsp and update-lsp, which map to actively-stateful PCEP
        operations using PCInitiate and PCUpd messages to initiate,
        destroy and udpate LSP configuration. The lifecycle of these
        instructions follows RFC8281 and RFC 8231, completing execution once the
        head-end router has acknowledged operation success. Should the router
        become disconnected, the instruction resolve to Cancelled if the
        message has not been sent into the TCP socket, or Failed it they have.

        Copyright (c)2013 Cisco Systems, Inc. All rights reserved.

        This program and the accompanying materials are made available
        under the terms of the Eclipse Public License v1.0 which
        accompanies this distribution, and is available at
        http://www.eclipse.org/legal/epl-v10.html";

    revision "2018-11-09" {
        description
            "P2MP extension.";
        reference "RFC8306";
    }

    revision 2017-10-25 {
        description "Update network-topology-pcep revision";
    }

    revision "2013-11-06" {
        description
            "Initial revision.";
        reference "";
    }

    rpc submit-add-lsp {
        input {
            uses ntp:topology-instruction-input;
            uses pcep:add-lsp-args;
        }
        output {
            uses ntp:topology-instruction-output;
        }
    }

    rpc submit-remove-lsp {
        input {
            uses ntp:topology-instruction-input;
            uses pcep:remove-lsp-args;
        }
        output {
            uses ntp:topology-instruction-output;
        }
    }

    rpc submit-update-lsp {
        input {
            uses ntp:topology-instruction-input;
            uses pcep:update-lsp-args;
        }
        output {
            uses ntp:topology-instruction-output;
        }
    }

    rpc submit-ensure-lsp-operational {
        input {
            uses ntp:topology-instruction-input;
            uses pcep:ensure-lsp-operational-args;
        }
        output {
            uses ntp:topology-instruction-output;
        }
    }

    rpc submit-trigger-sync {
        input {
            uses ntp:topology-instruction-input;
            uses pcep:trigger-sync-args;
        }
        output {
            uses ntp:topology-instruction-output;
        }
    }
}
