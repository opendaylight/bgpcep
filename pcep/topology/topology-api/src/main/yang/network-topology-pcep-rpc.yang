module network-topology-pcep-rpc {
    // vi: set et smarttab sw=4 tabstop=4:
    yang-version 1;
    namespace "urn:opendaylight:params:xml:ns:yang:network-topology-pcep-rpc";
    prefix "pcep-rpc";

    import network-topology { prefix nt; revision-date 2013-10-21; }
    import odl-network-topology { prefix ont; revision-date 2014-01-13; }

    organization "AT&T Services, Inc.";
    contact "Claudio D. Gasparini <claudio.gasparini@pantheon.sk>";

    description
        "This module contains the PCEP topology rpcs
         Copyright (c)2017 AT&T Services, Inc. All rights reserved.;

         This program and the accompanying materials are made available
         under the terms of the Eclipse Public License v1.0 which
         accompanies this distribution, and is available at
         http://www.eclipse.org/legal/epl-v10.html";

    revision "2017-11-10" {
        description
            "Initial revision.";
        reference "";
    }

    grouping node-id {
        leaf node {
            type nt:node-ref;
            mandatory true;
        }
    }

    rpc release-connection {
        description "Closes the session between PCE and PCC.";
        input {
            uses node-id;
        }
    }
}
