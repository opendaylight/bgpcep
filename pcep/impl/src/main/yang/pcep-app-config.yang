module pcep-app-config {
    namespace "urn:opendaylight:params:xml:ns:yang:controller:pcep:app-config";
    prefix "pcep-app-config";

    description
        "Configuration for the PCEP implementation.

         Copyright (c) 2016 Brocade Communications Systems, Inc. All rights reserved.

         This program and the accompanying materials are made available
         under the terms of the Eclipse Public License v1.0 which
         accompanies this distribution, and is available at
         http://www.eclipse.org/legal/epl-v10.html";

    revision "2016-07-07" {
        description
            "Initial revision.";
    }

    import pcep-config { prefix pc; }

    container pcep-session-config {
        // FIXME: BGPCEP-962: remove this container
        uses pc:pcep-session-timers;
    }

    container pcep-dispatcher-config {
        // FIXME: BGPCEP-962: remove this container

        uses pc:pcep-session-error-policy;

        container tls {
            presence true;
            uses pc:pcep-session-tls;
        }
    }
}
