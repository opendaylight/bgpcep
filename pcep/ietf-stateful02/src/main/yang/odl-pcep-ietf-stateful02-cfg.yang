// vi: set smarttab et sw=4 tabstop=4:
module odl-pcep-ietf-stateful02-cfg {
    yang-version 1;
    namespace "urn:opendaylight:params:xml:ns:yang:controller:pcep:stateful02:cfg";
    prefix "pcep-stateful02";

    import config { prefix config; revision-date 2013-04-05; }
    import odl-pcep-api-cfg { prefix pcep; revision-date 2013-04-09; }
    import odl-pcep-spi-cfg { prefix spi; revision-date 2013-11-15; }

    organization "Cisco Systems, Inc.";

    contact "Robert Varga <rovarga@cisco.com>";

    description
        "This module contains the base YANG definitions for
         draft-ietf-pce-stateful-pce-02 extensions.

        Copyright (c)2013 Cisco Systems, Inc. All rights reserved.;

        This program and the accompanying materials are made available
        under the terms of the Eclipse Public License v1.0 which
        accompanies this distribution, and is available at
        http://www.eclipse.org/legal/epl-v10.html";

    revision "2014-02-21" {
        description
            "Updated revision dates for imports.";
    }

    identity pcep-session-proposal-factory-stateful02 {
        base config:module-type;
        config:java-name-prefix "Stateful02PCEPSessionProposalFactory";
        config:provided-service pcep:pcep-session-proposal-factory;
    }

    augment "/config:modules/config:module/config:configuration" {
        case pcep-session-proposal-factory-stateful02 {
            when "/config:modules/config:module/config:type = 'pcep-session-proposal-factory-stateful02'";

            leaf dead-timer-value {
                type uint8;
                default 120;
            }

            leaf keep-alive-timer-value {
                type uint8;
                default 30;
            }

            leaf initiated {
                type boolean;
                default true;
            }

            leaf stateful {
                type boolean;
                default true;
            }

            leaf active {
                type boolean;
                default true;
            }

            leaf timeout {
                type uint16;
                default 180;
            }
        }
    }

    identity pcep-parser-ietf-stateful02 {
        base config:module-type;
        config:provided-service spi:extension;
        config:java-name-prefix IetfStateful02PCEPParser;
    }

    augment "/config:modules/config:module/config:configuration" {
        case pcep-parser-ietf-stateful02 {
            when "/config:modules/config:module/config:type = 'pcep-parser-ietf-stateful02'";
        }
    }

    identity pcep-parser-crabbe-initiated00 {
        base config:module-type;
        config:provided-service spi:extension;
        config:java-name-prefix CrabbeInitiated00PCEPParser;
    }

    augment "/config:modules/config:module/config:configuration" {
        case pcep-parser-crabbe-initiated00 {
            when "/config:modules/config:module/config:type = 'pcep-parser-crabbe-initiated00'";
        }
    }
}
