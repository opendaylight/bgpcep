module odl-pcep-crabbe-initiated00 {
    yang-version 1;
    namespace "urn:opendaylight:params:xml:ns:yang:pcep:crabbe:initiated:00";
    prefix "initiated00";

    import pcep-types { prefix pcep; revision-date 2013-10-05; }
    import pcep-message { prefix msg; revision-date 2013-10-07; }
    import network-topology { prefix nt; revision-date 2013-10-21; }
    import network-topology-pcep { prefix topo; revision-date 2013-10-24; }
    import odl-pcep-ietf-stateful02 { prefix stateful; revision-date 2014-01-10 ;}

    organization "Cisco Systems, Inc.";
    contact "Dana Kutenicsova <dkutenic@cisco.com>";

    description
        "This module contains the data model of PCEP extensions defined
        in draft-crabbe-pce-pce-initiated-lsp-00.

        Copyright (c)2014 Cisco Systems, Inc. All rights reserved.

        This program and the accompanying materials are made available
        under the terms of the Eclipse Public License v1.0 which
        accompanies this distribution, and is available at
        http://www.eclipse.org/legal/epl-v10.html";

    revision "2014-01-13" {
        description
            "Initial revision.";
        reference "https://tools.ietf.org/html/draft-crabbe-pce-pce-initiated-lsp-00";
    }

    grouping pcinitiate-message {
        uses pcep:message;

        container pcinitiate-message {
            description "LSP Initiate Message";
            reference "http://tools.ietf.org/html/draft-crabbe-pce-pce-initiated-lsp-00#section-5.1";

            uses pcep:message-header;

            list requests {
                uses pcep:endpoints-object;

                uses pcep:explicit-route-object;

                uses pcep:lsp-attributes;
            }
        }
    }

    grouping lsp-cleanup-tlv {
        description "LSP Cleanup TLV";
        reference "http://tools.ietf.org/html/draft-crabbe-pce-pce-initiated-lsp-00#section-6.2.1";
        container lsp-cleanup {
            uses pcep:tlv;
            leaf timeout {
                type uint32 {
                    range 0..4294967295;
                }
                mandatory true;
            }
        }
    }

    grouping initiated-capability-tlv {
        leaf initiation {
            type boolean;
            default false;
        }
    }

    augment "/msg:open/msg:open-message/msg:open/msg:tlvs" {
        uses lsp-cleanup-tlv;
    }

    augment "/msg:open/msg:open-message/msg:open/msg:tlvs/stateful:stateful" {
        uses initiated-capability-tlv;
    }

    augment "/pcinitiate/pcinitiate-message/requests/lspa/tlvs" {
        uses stateful:symbolic-path-name-tlv;
    }

    notification pcinitiate {
        uses pcinitiate-message;
    }

    augment "/nt:network-topology/nt:topology/nt:node/topo:path-computation-client/topo:stateful-tlv/stateful:stateful" {
        uses initiated-capability-tlv;
    }
}
