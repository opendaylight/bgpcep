module pcep-p2mp-te-lsp-config {
    yang-version 1;
    namespace "urn:opendaylight:params:xml:ns:yang:controller:pcep:p2mp:te:lsp:config";
    prefix "pcep-p2mp-config";

    description
        "Configuration for the PCEP p2mp te lsp extension.
         Copyright (c)2018 AT&T Services, Inc. All rights reserved.;

         This program and the accompanying materials are made available
         under the terms of the Eclipse Public License v1.0 which
         accompanies this distribution, and is available at
         http://www.eclipse.org/legal/epl-v10.html";

    organization "AT&T Services, Inc.";
    contact "Claudio D. Gasparini <claudio.gasparini@pantheon.sk>";

    revision "2018-11-07" {
        description "Initial revision";
    }

    container pcep-p2mp-te-lsp-config {
        leaf path-computation-capable {
            description "Advertize pcep-p2mp-te-lsp path computation capability";
            type boolean;
            default false;
        }
    }
}
