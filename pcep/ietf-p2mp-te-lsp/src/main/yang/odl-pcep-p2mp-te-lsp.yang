module odl-pcep-p2mp-te-lsp {
    yang-version 1;
    // FIXME: rename module/namespace to odl-pcep-rfc8306
    namespace "urn:opendaylight:params:xml:ns:yang:pcep:p2mp:te:lsp";
    prefix "pcep-p2mp";

    import odl-pcep-types { prefix pcep; revision-date 2025-09-30; }
    import odl-pcep-message { prefix msg; revision-date 2025-09-30; }
    import odl-codegen-extensions { prefix oce; }

    description
        "This module contains the data model of PCEP extensions defined
         in RFC8306.

         Copyright (c)2018 AT&T Services, Inc. All rights reserved.;

         This program and the accompanying materials are made available
         under the terms of the Eclipse Public License v1.0 which
         accompanies this distribution, and is available at
         http://www.eclipse.org/legal/epl-v10.html";

    organization "AT&T Services, Inc.";
    contact "Claudio D. Gasparini <claudio.gasparini@pantheon.sk>";

    revision "2018-11-09" {
        description "Initial revision";
    }

    grouping p2mp-pce-capability-tlv {
        description "P2MP-PCE-CAPABILITY TLV";
        reference "https://tools.ietf.org/html/rfc8306#section-3.1.2";

        container p2mp-pce-capability {
            uses pcep:tlv;
            presence
                "Capability indicates that the sender can perform P2MP path computations";
        }
    }

    augment "/msg:open/msg:open-message/msg:open/msg:tlvs" {
        reference "https://tools.ietf.org/html/rfc8306#section-3.1.2";
        uses p2mp-pce-capability-tlv;
        oce:augment-identifier tlvs-p2mp-capability-aug;
    }

    augment "/msg:pcerr/msg:pcerr-message/msg:error-type/msg:session-case/msg:session/msg:open/msg:tlvs" {
        reference "https://tools.ietf.org/html/rfc8306#section-3.1.2";
        uses p2mp-pce-capability-tlv;
        oce:augment-identifier tlvs-p2mp-capability-error-aug;
    }
}
