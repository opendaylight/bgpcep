// vi: set smarttab et sw=4 tabstop=4:
module topology-tunnel-pcep-config {
    yang-version 1.1;
    namespace "urn:opendaylight:params:xml:ns:yang:topology:tunnel:pcep:config";
    prefix ttpc;

    import network-topology { prefix nt; revision-date 2013-10-21; }
    import topology-tunnel-pcep { prefix ttp; revision-date 2018-11-09; }
    import odl-codegen-extensions { prefix oce; }

    description
        "This module contains the PCEP Tunnel config extensions to base topology model.
         Copyright (c)2017 AT&T Services, Inc. All rights reserved.;

         This program and the accompanying materials are made available
         under the terms of the Eclipse Public License v1.0 which
         accompanies this distribution, and is available at
         http://www.eclipse.org/legal/epl-v10.html";

    organization "AT&T Services, Inc.";
    contact "Claudio D. Gasparini <claudio.gasparini@pantheon.sk>";

    revision "2018-11-09" {
        description
            "P2MP extension.";
        reference "RFC8306";
    }

    revision "2017-11-27" {
        description
            "Initial revision.";
    }

    grouping topology-ref {
        leaf pcep-topology-reference {
        description "An absolute reference to a topology instance.";
        type leafref {
            path "/nt:network-topology/nt:topology/nt:topology-id";
            require-instance true;
            }
        }
    }

    augment "/nt:network-topology/nt:topology" {
        when "nt:topology-types/ttp:topology-tunnel-pcep";
        oce:augment-identifier pcep-tunnel-topology-config;
        description "Augment Pcep topology with session config";

        uses topology-ref;
    }
}
