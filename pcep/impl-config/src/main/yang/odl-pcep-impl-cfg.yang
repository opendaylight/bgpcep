// vi: set smarttab et sw=4 tabstop=4:
module odl-pcep-impl-cfg {
    yang-version 1;
    namespace "urn:opendaylight:params:xml:ns:yang:controller:pcep:impl";
    prefix "pcep-impl";

    import config { prefix config; revision-date 2013-04-05; }
    import pcep { prefix pcep; revision-date 2013-04-09; }
    import config-pcep-spi { prefix spi; revision-date 2013-11-15; }
    import netty { prefix netty; revision-date 2013-11-19; }

    organization "Cisco Systems, Inc.";

    contact "Robert Varga <rovarga@cisco.com>";

    description
        "This module contains the base YANG definitions for
         PCEP implementation.

        Copyright (c)2013 Cisco Systems, Inc. All rights reserved.;

        This program and the accompanying materials are made available
        under the terms of the Eclipse Public License v1.0 which
        accompanies this distribution, and is available at
        http://www.eclipse.org/legal/epl-v10.html";

    revision "2013-06-27" {
        description
            "Updated revision dates for imports.";
    }

    revision "2013-04-09" {
        description
            "Initial revision";
    }

    identity pcep-parser-base {
        base config:module-type;
        config:provided-service spi:extension;
        config:java-name-prefix BasePCEPParser;
    }

    augment "/config:modules/config:module/config:configuration" {
        case pcep-parser-base {
            when "/config:modules/config:module/config:type = 'pcep-parser-base'";
        }
    }

    identity pcep-parser-ietf-stateful07 {
        base config:module-type;
        config:provided-service spi:extension;
       config:java-name-prefix IetfStateful07PCEPParser;
    }

    augment "/config:modules/config:module/config:configuration" {
        case pcep-parser-ietf-stateful07 {
            when "/config:modules/config:module/config:type = 'pcep-parser-ietf-stateful07'";
        }
    }

	identity pcep-parser-ietf-initiated00 {
		base config:module-type;
        config:provided-service spi:extension;
        config:java-name-prefix IetfInitiated00PCEPParser;
    }

    augment "/config:modules/config:module/config:configuration" {
        case pcep-parser-ietf-initiated00 {
            when "/config:modules/config:module/config:type = 'pcep-parser-ietf-initiated00'";
	    }
    }

    identity pcep-parser-ietf-stateful02 {
        base config:module-type;
        config:provided-service spi:extension;
        config:java-name-prefix IetfStateful02PCEPParser;
    }

    augment "/config:modules/config:module/config:configuration" {
        case pcep-parser-ietf-stateful02 {
            when "/config:modules/config:module/config:type = 'pcep-parser-ietf-stateful02'";
        }
    }

	identity pcep-parser-crabbe-initiated00 {
		base config:module-type;
        config:provided-service spi:extension;
        config:java-name-prefix CrabbeInitiated00PCEPParser;
    }

    augment "/config:modules/config:module/config:configuration" {
        case pcep-parser-crabbe-initiated00 {
            when "/config:modules/config:module/config:type = 'pcep-parser-crabbe-initiated00'";
        }
    }

    identity pcep-dispatcher-impl {
        base config:module-type;
        config:provided-service pcep:pcep-dispatcher;
        config:java-name-prefix PCEPDispatcherImpl;
    }

    augment "/config:modules/config:module/config:configuration" {
        case pcep-dispatcher-impl {
            when "/config:modules/config:module/config:type = 'pcep-dispatcher-impl'";

            leaf max-unknown-messages {
                type uint16;
                default 5;
            }

            container pcep-extensions {
                uses config:service-ref {
                    refine type {
                        mandatory true;
                        config:required-identity spi:consumer-extensions;
                    }
                }
            }

            container pcep-session-proposal-factory {
                uses config:service-ref {
                    refine type {
                        mandatory true;
                        config:required-identity pcep:pcep-session-proposal-factory;
                    }
                }
            }

            container boss-group {
                uses config:service-ref {
                    refine type {
                        mandatory true;
                        config:required-identity netty:netty-threadgroup;
                    }
                }
            }

            container worker-group {
                uses config:service-ref {
                    refine type {
                        mandatory true;
                        config:required-identity netty:netty-threadgroup;
                    }
                }
            }

            container timer {
                uses config:service-ref {
                    refine type {
                        mandatory true;
                        config:required-identity netty:netty-timer;
                    }
                }
            }
        }
    }

    identity pcep-session-proposal-factory-impl {
        base config:module-type;
        config:java-name-prefix "PCEPSessionProposalFactoryImpl";
        config:provided-service pcep:pcep-session-proposal-factory;
    }

    augment "/config:modules/config:module/config:configuration" {
        case pcep-session-proposal-factory-impl {
            when "/config:modules/config:module/config:type = 'pcep-session-proposal-factory-impl'";

            leaf dead-timer-value {
                type uint16;
                default 120;
            }

            leaf keep-alive-timer-value {
                type uint16;
                default 30;
            }
        }
    }
}
