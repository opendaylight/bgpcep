module odl-pcep-lsp-setup-type01 {
    yang-version 1;
    namespace "urn:opendaylight:params:xml:ns:yang:pcep:lsp:setup:type:01";
    prefix "lst01";

    import pcep-types { prefix pcep; revision-date 2013-10-05; }
    import pcep-message { prefix msg; revision-date 2013-10-07; }
    import odl-pcep-ietf-stateful07 { prefix stateful; revision-date 2013-12-22; }
    import odl-pcep-ietf-initiated00 { prefix crabbe; revision-date 2013-11-26; }
    import ietf-inet-types { prefix inet; revision-date 2010-09-24; }
    import yang-ext { prefix ext; revision-date 2013-07-09; }

    organization "Cisco Systems, Inc.";
    contact "Milos Fabian <milfabia@cisco.com>";

    description
        "This module contains the data model of path setup type in PCEP messages,
        draft-sivabalan-pce-lsp-setup-type-01.

        Copyright (c)2014 Cisco Systems, Inc. All rights reserved.

        This program and the accompanying materials are made available
        under the terms of the Eclipse Public License v1.0 which
        accompanies this distribution, and is available at
        http://www.eclipse.org/legal/epl-v10.html";

    revision "2014-05-07" {
        description
            "Initial revision.";
        reference "http://tools.ietf.org/html/draft-sivabalan-pce-lsp-setup-type-01";
    }

    grouping path-setup-type-tlv {
        description "PATH-SETUP-TYPE TLV";
        reference "http://tools.ietf.org/html/draft-sivabalan-pce-lsp-setup-type-01#section-3";

        container path-setup-type {
            uses pcep:tlv;
            leaf pst {
                description "PST=0(false): Path is setup via RSVP-TE signaling protocol(default).
                    PST=1(true): Path is setup using Segment Routing technique.";
                type boolean;
                default false;
            }
        }
    }

    augment "/msg:pcreq/msg:pcreq-message/msg:requests/msg:rp/msg:tlvs" {
        reference "http://tools.ietf.org/html/draft-sivabalan-pce-lsp-setup-type-01#section-3";
        uses path-setup-type-tlv;
        ext:augment-identifier tlvs-1;
    }

    augment "/msg:pcrep/msg:pcrep-message/msg:replies/msg:rp/msg:tlvs" {
        reference "http://tools.ietf.org/html/draft-sivabalan-pce-lsp-setup-type-01#section-3";
        uses path-setup-type-tlv;
        ext:augment-identifier tlvs-2;
    }

    augment "/msg:pcntf/msg:pcntf-message/msg:notifications/msg:rps/msg:rp/msg:tlvs" {
        reference "http://tools.ietf.org/html/draft-sivabalan-pce-lsp-setup-type-01#section-3";
        uses path-setup-type-tlv;
        ext:augment-identifier tlvs-3;
    }

    augment "/msg:pcerr/msg:pcerr-message/msg:error-type/msg:request-case/msg:request/msg:rps/msg:rp/msg:tlvs" {
        reference "http://tools.ietf.org/html/draft-sivabalan-pce-lsp-setup-type-01#section-3";
        uses path-setup-type-tlv;
        ext:augment-identifier tlvs-4;
    }

    augment "/crabbe:pcinitiate/crabbe:pcinitiate-message/crabbe:requests/crabbe:srp/crabbe:tlvs" {
        reference "http://tools.ietf.org/html/draft-sivabalan-pce-lsp-setup-type-01#section-3";
        uses path-setup-type-tlv;
        ext:augment-identifier tlvs-5;
    }

    augment "/stateful:pcupd/stateful:pcupd-message/stateful:updates/stateful:srp/stateful:tlvs" {
        reference "http://tools.ietf.org/html/draft-sivabalan-pce-lsp-setup-type-01#section-3";
        uses path-setup-type-tlv;
        ext:augment-identifier tlvs-6;
    }

    augment "/stateful:pcrpt/stateful:pcrpt-message/stateful:reports/stateful:srp/stateful:tlvs" {
        reference "http://tools.ietf.org/html/draft-sivabalan-pce-lsp-setup-type-01#section-3";
        uses path-setup-type-tlv;
        ext:augment-identifier tlvs-7;
    }

    augment "/msg:pcerr/msg:pcerr-message/msg:error-type/stateful:stateful-case/stateful:stateful/stateful:srps/stateful:srp/stateful:tlvs" {
        reference "http://tools.ietf.org/html/draft-sivabalan-pce-lsp-setup-type-01#section-3";
        uses path-setup-type-tlv;
        ext:augment-identifier tlvs-8;
    }
}
