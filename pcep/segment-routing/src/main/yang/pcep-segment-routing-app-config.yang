module pcep-segment-routing-app-config {
    namespace "urn:opendaylight:params:xml:ns:yang:controller:pcep:segment-routing-app-config";
    prefix "pcep-segment-routing-app-config";

    description
      "Configuration for the PCEP segment routing extension.

       Copyright (c) 2016 Brocade Communications Systems, Inc. All rights reserved.

       This program and the accompanying materials are made available
       under the terms of the Eclipse Public License v1.0 which
       accompanies this distribution, and is available at
       http://www.eclipse.org/legal/epl-v10.html";

    revision "2023-01-15" {
        description "Removed sr-capable leaf.";
    }

    revision "2016-07-07" {
        description "Initial revision.";
    }

    container pcep-segment-routing-config {
        leaf iana-sr-subobjects-type {
            description "If true (default) IANA Types for SR-ERO type (=36) and SR-RRO type (=36) are used,
                    else historical types (5 & 6) are used for parsing/serialization";
            type boolean;
            default true;
        }
    }
}
