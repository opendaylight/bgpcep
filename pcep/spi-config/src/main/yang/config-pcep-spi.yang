// vi: set smarttab et sw=4 tabstop=4:
module config-pcep-spi {
    yang-version 1;
    namespace "urn:opendaylight:params:xml:ns:yang:controller:pcep:spi";
    prefix "spi";

    import config { prefix config; revision-date 2013-04-05; }

    organization "Cisco Systems, Inc.";

    contact "Robert Varga <rovarga@cisco.com>";

    description
        "This module contains the base YANG definitions for
        PCEP SPI module.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity consumer-extensions {
        description
            "Service representing a PCEP parser extension registry. Extension
            consumers have this service injected.";

        base "config:service-type";
        config:java-class "org.opendaylight.protocol.pcep.spi.PCEPExtensionConsumerContext";
    }

    identity extensions {
        description
            "Service representing a PCEP parser extension registry. Extension
            providers have this service injected for registration.";

        base "consumer-extensions";
        config:java-class "org.opendaylight.protocol.pcep.spi.PCEPExtensionProviderContext";
    }

    identity extension {
        description
            "Service representing a PCEP parser extension.";

        base "config:service-type";
        config:java-class "org.opendaylight.protocol.pcep.spi.PCEPExtensionProviderActivator";
    }

    identity pcep-extensions-impl {
        base config:module-type;
        config:provided-service extensions;
        config:java-name-prefix SimplePCEPExtensionProviderContext;
    }

    augment "/config:modules/config:module/config:configuration" {
        case pcep-extensions-impl {
            when "/config:modules/config:module/config:type = 'pcep-extensions-impl'";

            list extension {
                uses config:service-ref {
                    refine type {
                        mandatory true;
                        config:required-identity extension;
                    }
                }
            }
        }
    }
}
