// vi: set smarttab et sw=4 tabstop=4:
module odl-pcep-topology-provider-cfg {
    yang-version 1;
    namespace "urn:opendaylight:params:xml:ns:yang:controller:pcep:topology:provider";
    prefix "p2p";

    import config { prefix config; revision-date 2013-04-05; }
    import odl-programming-spi-cfg { prefix pgmspi; revision-date 2013-11-15; }
    import odl-topology-api-cfg { prefix topo; revision-date 2013-11-15; }
    import ietf-inet-types { prefix inet; revision-date 2010-09-24; }
    import network-topology { prefix nt; revision-date 2013-10-21; }
    import odl-pcep-api-cfg { prefix pcep; revision-date 2013-04-09; }
    import opendaylight-md-sal-binding { prefix mdsal; revision-date 2013-10-28; }
    import rpc-context { prefix rpcx; revision-date 2013-06-17; }
    import pcep-session-stats { prefix pcep-stats; revision-date 2014-10-06; }
    import rfc2385 { prefix rfc2385; revision-date 2016-03-24; }

    organization "Cisco Systems, Inc.";

    contact "Robert Varga <rovarga@cisco.com>";

    description
        "This module contains the base YANG definitions for
        PCEP topology provider service.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity pcep-topology-stateful {
        description
            "Service representing a stateful draft support module";

        base "config:service-type";
        config:java-class "org.opendaylight.bgpcep.pcep.topology.provider.TopologySessionListenerFactory";
    }

    identity pcep-topology-stateful07 {
        base config:module-type;
        config:provided-service pcep-topology-stateful;
        config:java-name-prefix Stateful07TopologySessionListener;
    }

    augment "/config:modules/config:module/config:configuration" {
        case pcep-topology-stateful07 {
            when "/config:modules/config:module/config:type = 'pcep-topology-stateful07'";
        }
    }

    identity pcep-topology-reference {
        description
            "Service representing a PCEP-enabled topology.";

        // FIXME: should be a topology-reference, really
        //base "topo:topology-reference";
        base "config:service-type";
        config:java-class "org.opendaylight.bgpcep.topology.TopologyReference";
    }

    identity pcep-topology-provider {
        base config:module-type;
        config:provided-service pcep-topology-reference;
        config:java-name-prefix PCEPTopologyProvider;
    }

    augment "/config:modules/config:module/config:configuration" {
        case pcep-topology-provider {
            when "/config:modules/config:module/config:type = 'pcep-topology-provider'";

            container data-provider {
                uses config:service-ref {
                    refine type {
                        mandatory true;
                        config:required-identity mdsal:binding-async-data-broker;
                    }
                }
            }

            container rpc-registry {
                uses config:service-ref {
                    refine type {
                        mandatory true;
                        config:required-identity mdsal:binding-rpc-registry;
                    }
                }
            }

            container dispatcher {
                uses config:service-ref {
                    refine type {
                        mandatory true;
                        config:required-identity pcep:pcep-dispatcher;
                    }
                }
            }

            container scheduler {
                uses config:service-ref {
                    refine type {
                        mandatory true;
                        config:required-identity pgmspi:instruction-scheduler;
                    }
                }
            }

            container stateful-plugin {
                uses config:service-ref {
                    refine type {
                        mandatory true;
                        config:required-identity pcep-topology-stateful;
                    }
                }
            }

            leaf topology-id {
                type nt:topology-id;
                mandatory true;
            }

            leaf listen-address {
                type inet:ip-address;
                default "0.0.0.0";
            }

            leaf listen-port {
                type inet:port-number;
                default 4189;
            }

            list client {
                leaf address {
                    type inet:ip-address;
                }
                key "address";

                leaf password {
                    type rfc2385:rfc2385-key;
                    description "RFC2385 shared secret";
                }
            }

            leaf rpc-timeout {
                type int16;
                default 30;
            }
        }
    }

    identity session-rpc;

    grouping stateful-preferences {
        leaf instantiation {
            description "Represents peer's instantiation capability.";
            type boolean;
            default "false";
        }

        leaf stateful {
            description "Represents peer's stateful/stateless capability.";
            type boolean;
            default "false";
        }

        leaf active {
            description "Represents peer's LSP update capability.";
            type boolean;
            default "false";
        }
    }

    augment "/config:modules/config:module/config:state" {
        case pcep-topology-provider {
            when "/config:modules/config:module/config:type = 'pcep-topology-provider'";
            list listener-state {
                description "Statistics gained from session listener.";
                config:inner-state-bean;
                rpcx:rpc-context-instance "session-rpc";

                key "peer-id";

                leaf peer-id {
                    type string;
                }

                container session-state {
                    leaf session-duration {
                        description "Elapsed time (in d:H:m:s) from session-up until now.";
                        type string;
                    }
                    uses pcep-stats:pcep-session-state;
                }

                container peer-capabilities {
                    description "Remote peer's (PCC) advertised stateful capabilities.";
                    uses stateful-preferences;
                }

                leaf delegated-lsps-count {
                    description "The number of delegated LSPs (tunnels) from PCC.";
                    type uint16;
                }

                leaf synchronized {
                    description "Represents synchronization status.";
                    type boolean;
                }

                container stateful-messages {
                    description "The statistics of sent/received PCEP stateful messages.";
                    leaf last-received-rpt-msg-timestamp {
                        description "The timestamp of last received PCRpt message.";
                        type uint32;
                    }

                    leaf received-rpt-msg-count {
                        description "The number of received PcRpt messages.";
                        type uint32;
                    }

                    leaf sent-upd-msg-count {
                        description "The number of sent PCUpd messages.";
                        type uint32;
                    }

                    leaf sent-init-msg-count {
                        description "The number of sent PCInitiate messages.";
                        type uint32;
                    }
                }

                container reply-time {
                    description "Measures time elapsed from request's send to reply's received.";

                    leaf average-time {
                        description "Average time (in milliseconds) of gauged values.";
                        type uint32;
                    }

                    leaf min-time {
                        description "Minimal measured time value (in milliseconds).";
                        type uint32;
                    }

                    leaf max-time {
                        description "Maximal measured time value (in milliseconds).";
                        type uint32;
                    }
                }
              }
          }
    }

    rpc tear-down-session {
        description "Closes the session between PCE and PCC.";
        input {
            uses rpcx:rpc-context-ref {
                refine context-instance {
                    rpcx:rpc-context-instance session-rpc;
                }
            }
        }
    }

    rpc reset-stats {
        description "Resets statistics like message counters and timestamps. (set to 0)";
        input {
            uses rpcx:rpc-context-ref {
                refine context-instance {
                    rpcx:rpc-context-instance session-rpc;
                }
            }
        }
    }
}
