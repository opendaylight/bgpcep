// vi: set smarttab et sw=4 tabstop=4:
module odl-pcep-topology-provider-config {
    yang-version 1;
    namespace "urn:opendaylight:params:xml:ns:yang:odl:pcep:topology:provider:config";
    prefix odl-pcep-topology-provider-config;

    import network-topology { prefix nt; revision-date 2013-10-21; }
    import ietf-inet-types { prefix inet; revision-date 2013-07-15; }
    import rfc2385 { prefix rfc2385; revision-date 2016-03-24; }

    description
        "This module contains the base YANG definitions for
         PCEP topology provider service Configuration.
         Copyright (c) 2017 Pantheon Technologies s.r.o. and others.  All rights reserved.

         This program and the accompanying materials are made available
         under the terms of the Eclipse Public License v1.0 which
         accompanies this distribution, and is available at
         http://www.eclipse.org/legal/epl-v10.html";

    organization "Pantheon Technologies";
    contact "Claudio D. Gasparini <claudio.gasparini@pantheon.sk>";

    revision "2017-03-01" {
        description
            "Initial revision.";
    }

    container odl-pcep-topology-provider {
        list odl-pcep-topology-provider-config {
            key "topology-id";

            leaf topology-id {
                type nt:topology-id;
                mandatory true;
            }

            leaf scheduler-id {
                type string;
                mandatory true;
            }

            leaf listen-address {
                type inet:ip-address;
                default "0.0.0.0";
            }

            leaf listen-port {
                type inet:port-number;
                default 4189;
            }

            list client {
                leaf address {
                    type inet:ip-address;
                }
                key "address";

                leaf password {
                    type rfc2385:rfc2385-key;
                    description "RFC2385 shared secret";
                }
            }

            leaf rpc-timeout {
                type int16;
                default 30;
            }
        }
    }
}
