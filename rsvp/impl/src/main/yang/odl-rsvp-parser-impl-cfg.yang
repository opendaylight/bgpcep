// vi: set smarttab et sw=4 tabstop=4:
module odl-rsvp-parser-impl-cfg {
    yang-version 1;
    namespace "urn:opendaylight:params:xml:ns:yang:controller:rsvp:impl";
    prefix "rsvp-impl";

    import config { prefix config; revision-date 2013-04-05; }
    import odl-rsvp-parser-spi-cfg { prefix spi; revision-date 2015-08-26; }

    organization "Cisco Systems, Inc.";

    contact "Claudio D. Gasparini <cgaspari@cisco.com>";

    description
        "This module contains the base YANG definitions for
         RSPV listener service.

        Copyright (c)2015 Cisco Systems, Inc. All rights reserved.;

        This program and the accompanying materials are made available
        under the terms of the Eclipse Public License v1.0 which
        accompanies this distribution, and is available at
        http://www.eclipse.org/legal/epl-v10.html";

    revision "2015-08-26" {
         description
             "Initial revision";
    }

    identity rsvp-parser {
        base config:module-type;
        config:provided-service spi:rsvp-extension;
        config:java-name-prefix RSVPParser;
    }

    augment "/config:modules/config:module/config:configuration" {
        case rsvp-parser {
            when "/config:modules/config:module/config:type = 'rsvp-parser'";
        }
    }
}
