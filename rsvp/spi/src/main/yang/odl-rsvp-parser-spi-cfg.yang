// vi: set smarttab et sw=4 tabstop=4:
module odl-rsvp-parser-spi-cfg {
    yang-version 1;
    namespace "urn:opendaylight:params:xml:ns:yang:controller:rsvp:spi";
    prefix "rsvp-spi";

    import config { prefix config; revision-date 2013-04-05; }

    organization "Cisco Systems, Inc.";

    contact "Claudio D. Gasparini <cgaspari@cisco.com>";

    description
        "This module contains the base YANG definitions for
         RSPV listener implementation.

        Copyright (c)2015 Cisco Systems, Inc. All rights reserved.;

        This program and the accompanying materials are made available
        under the terms of the Eclipse Public License v1.0 which
        accompanies this distribution, and is available at
        http://www.eclipse.org/legal/epl-v10.html";

   revision "2015-08-26" {
        description
            "Initial revision";
    }

    identity consumer-extensions {
        description
            "Service representing a RSVP parser extension registry. Extension
            consumers have this service injected.";

        base "config:service-type";
        config:java-class "org.opendaylight.protocol.rsvp.parser.spi.RSVPExtensionConsumerContext";
    }

    identity rsvp-extensions {
        description
            "Service representing a RSVP parser extension registry. Extension
            providers have this service injected for registration.";

        base "consumer-extensions";
        config:java-class "org.opendaylight.protocol.rsvp.parser.spi.RSVPExtensionProviderContext";
    }

    identity rsvp-extensions-impl {
        base config:module-type;
        config:provided-service rsvp-extensions;
        config:java-name-prefix SimpleRSVPExtensionProviderContext;
    }

    augment "/config:modules/config:module/config:configuration" {
        case rsvp-extensions-impl {
            when "/config:modules/config:module/config:type = 'rsvp-extensions-impl'";
        }
    }
}
