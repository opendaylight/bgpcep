module ieee754 {
    yang-version 1;
    namespace "urn:opendaylight:params:xml:ns:yang:ieee754";
    prefix "ieee754";

    organization "Cisco Systems, Inc.";
    contact "Robert Varga <rovarga@cisco.com>";

    description
        "This module contains the definition of basic float types.

        Copyright (c)2013 Cisco Systems, Inc. All rights reserved.

        This program and the accompanying materials are made available
        under the terms of the Eclipse Public License v1.0 which
        accompanies this distribution, and is available at
        http://www.eclipse.org/legal/epl-v10.html";

    revision "2013-08-19" {
        description "Initial revision.";
        reference "IEEE 754-2008";
    }

    typedef float32 {
        type binary {
            length 4;
        }
    }

    typedef float64 {
        type binary {
            length 8;
        }
    }

    typedef float128 {
        type binary {
            length 16;
        }
    }
}
