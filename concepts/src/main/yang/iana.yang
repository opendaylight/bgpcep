module iana {
    yang-version 1;
    namespace "urn:opendaylight:params:xml:ns:yang:iana";
    prefix "iana";

    organization "Cisco Systems, Inc.";
    contact "Robert Varga <rovarga@cisco.com>";

    description
        "This module contains the definition of types related to
         Internet Assigned Numbers Authority.

         Copyright (c)2013 Cisco Systems, Inc. All rights reserved.

         This program and the accompanying materials are made available
         under the terms of the Eclipse Public License v1.0 which
         accompanies this distribution, and is available at
         http://www.eclipse.org/legal/epl-v10.html";

    revision "2013-08-16" {
        description "Initial revision.";
        reference "https://www.iana.org/";
    }

    typedef enterprise-number {
        description "Private enterprise number.";
        reference "https://www.iana.org/assignments/enterprise-numbers/enterprise-numbers";
        type uint32;
    }
}
