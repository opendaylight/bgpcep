module odl-uint24 {
    yang-version 1;
    namespace "urn:opendaylight:params:xml:ns:yang:uint24";
    prefix "uint24";

    organization "OpenDaylight";
    contact "Robert Varga <robert.varga@pantheon.tech>";

    description
        "This module contains the definition of uint24, an uint32 restricted
         to 24 bits.

         Copyright (c)2019 PANTHEON.tech, s.r.o and others. All rights reserved.

         This program and the accompanying materials are made available
         under the terms of the Eclipse Public License v1.0 which
         accompanies this distribution, and is available at
         http://www.eclipse.org/legal/epl-v10.html";

    revision "2020-01-04" {
        description "Initial revision.";
    }

    typedef uint24 {
        type uint32 {
            range "0..16777215";
        }
        description "24-bit unsigned integer.";
    }
}
