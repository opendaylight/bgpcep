// vi: set smarttab et sw=4 tabstop=4:
module odl-tcpmd5-cfg {
    yang-version 1;
    namespace "urn:opendaylight:params:xml:ns:yang:controller:tcpmd5:cfg";
    prefix "tcpmd5";

    import config { prefix config; revision-date 2013-04-05; }

    organization "Cisco Systems, Inc.";

    contact "Robert Varga <rovarga@cisco.com>";

    description
        "This module contains the base YANG definitions for
         TCP MD5 Signature option.

        Copyright (c)2013 Cisco Systems, Inc. All rights reserved.;

        This program and the accompanying materials are made available
        under the terms of the Eclipse Public License v1.0 which
        accompanies this distribution, and is available at
        http://www.eclipse.org/legal/epl-v10.html";

    revision "2014-04-27" {
        description
            "Initial revision";
    }

    identity key-access-factory {
        description
            "Service representing a way for accessing key informtion.";

        base "config:service-type";
        config:java-class "org.opendaylight.bgpcep.tcpmd5.KeyAccessFactory";
    }

    typedef rfc2385-key {
        type string {
            length 1..80;
        }
    }
}
