// vi: set smarttab et sw=4 tabstop=4:
module odl-data-change-counter-cfg {
    yang-version 1;
    namespace "urn:opendaylight:params:xml:ns:yang:controller:bgpcep:data:change:counter";
    prefix "dcc-cfg";

    import config { prefix config; revision-date 2013-04-05; }
    import opendaylight-md-sal-binding { prefix mdsal; revision-date 2013-10-28; }

    organization "Cisco Systems, Inc.";

    contact "Milos Fabian <milfabia@cisco.com>";

    description
        "This module contains the base YANG definitions for
         topology data-change counter.

        Copyright (c)2014 Cisco Systems, Inc. All rights reserved.;

        This program and the accompanying materials are made available
        under the terms of the Eclipse Public License v1.0 which
        accompanies this distribution, and is available at
        http://www.eclipse.org/legal/epl-v10.html";

    revision "2016-03-15" {
        description
            "Updated to support multiple instances";
    }
    revision "2014-08-15" {
        description
            "Initial revision";
    }

    identity data-change-counter-impl {
        base config:module-type;
        config:java-name-prefix DataChangeCounterImpl;
    }

    augment "/config:modules/config:module/config:configuration" {
        case data-change-counter-impl {
            when "/config:modules/config:module/config:type = 'data-change-counter-impl'";

            leaf counter-id {
                type string;
            }

            leaf topology-name {
                type string;
            }

            container data-provider {
                uses config:service-ref {
                    refine type {
                        mandatory true;
                        config:required-identity mdsal:binding-async-data-broker;
                    }
                }
            }
        }
    }
}
