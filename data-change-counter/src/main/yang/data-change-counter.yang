module data-change-counter {
    yang-version 1;
    namespace "urn:opendaylight:params:xml:ns:yang:bgp-data-change-counter";
    prefix "bgp-dcc";

    organization "Cisco Systems, Inc.";
    contact "Milos Fabian <milfabia@cisco.com>";

    description
        "This module contains the base data model of a topology
        data-change counter. The module servers for testing purposes.

        Copyright (c)2014 Cisco Systems, Inc. All rights reserved.

        This program and the accompanying materials are made available
        under the terms of the Eclipse Public License v1.0 which
        accompanies this distribution, and is available at
        http://www.eclipse.org/legal/epl-v10.html";

    revision "2014-08-15" {
        description
            "Initial revision.";
    }

    container data-change-counter {
        leaf count {
            type uint32;
            description
                "The number of data changes.";
        }
    }
 }
