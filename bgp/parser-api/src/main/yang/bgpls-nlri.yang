module bgpls-nlri {
	yang-version 1;
	namespace "urn:opendaylight:params:xml:ns:yang:bgpls";
	prefix "nlri";

	import ietf-inet-types {
		prefix inet;
		revision-date 2010-09-24;
	}

	import bgp-linkstate {
		prefix bgp-ls;
	}

	import nps-concepts {
		prefix nps-c;
	}

	organization "Cisco Systems, Inc.";
	contact "Dana Kutenicsova <dkutenic@cisco.com>";

	description
		"This module contains the base data model of a BGP-LS Update message.
		It rolls up the definitions contained in RFC4271
		and draft-ietf-idr-ls-distribution-03.

		Copyright (c)2013 Cisco Systems, Inc. All rights reserved.

		This program and the accompanying materials are made available
		under the terms of the Eclipse Public License v1.0 which
		accompanies this distribution, and is available at
		http://www.eclipse.org/legal/epl-v10.html";

	revision "2013-08-12" {
		description
			"Initial revision.";
		reference "RFC4271";
	}

	typedef unnumbered-link-identifier {
		reference "http://tools.ietf.org/html/rfc4202#section-2.1";
		type uint32;
	}

	grouping link-anchor {
		container node-identifier {
			uses bgp-ls:node-identifier;
		}
		choice interface-identifier {
			case ipv4-iface-id {
				leaf ipv4-iface-id {
					type bgp-ls:ipv4-interface-identifier;
				}
			}

			case ipv6-iface-id {
				leaf ipv6-iface-id {
					type bgp-ls:ipv6-interface-identifier;
				}
			}

			case ospf-iface-id {
				leaf ospf-iface-id {
					type bgp-ls:ospf-interface-identifier;
				}
			}

			case unnum-iface-id {
				leaf unnum-iface-id {
					type unnumbered-link-identifier;
				}
			}
		}
	}

	grouping link-identifier {
		leaf topology-identifier {
			type bgp-ls:topology-identifier;
		}
		container link-anchor {
			uses link-anchor;
		}
	}

	grouping prefix-identifier {
		container node-identifier {
			uses bgp-ls:node-identifier;
		}
		leaf prefix {
			type inet:ip-prefix;
		}
	}

	grouping ospf-prefix-identifier {
		uses prefix-identifier;
		leaf ospf-route-t {
			type bgp-ls:ospf-route-type;
		}
	}

	grouping network-prefix-state {
		reference "http://tools.ietf.org/html/draft-ietf-idr-ls-distribution-03#section-3.3.3";
		leaf prefix-metric {
			type nps-c:metric;
		}
		leaf-list route-tags {
			type bgp-ls:route-tag;
		}
	}

	grouping ospf-network-prefix-state {
		uses network-prefix-state;
		leaf ospf-forwarding-address {
			type inet:ip-address;
		}
	}

	grouping is-is-network-prefix-state {
		uses network-prefix-state;
		container igp-bits {
			uses bgp-ls:igp-bits;
		}
		leaf-list extended-route-tags {
			type bgp-ls:extended-route-tag;
		}
	}

	grouping network-node {
		container network-node-state {
			uses bgp-ls:node-state;
		}
	}

	grouping network-link {
		container network-link-state {
			uses bgp-ls:link-state;
		}
	}

	grouping network-prefix {
		container network-prefix-state {
			uses network-prefix-state;
		}
	}

	notification bgpls-pdu {
		reference "http://tools.ietf.org/html/draft-ietf-idr-ls-distribution-03#section-3.2";
		leaf distinguisher {
			type bgp-ls:route-distinguisher;
		}
		leaf protocol {
			type bgp-ls:protocol-id;
			mandatory true;
		}
		leaf identifier {
			type bgp-ls:identifier;
		}
		choice objects {
			case nodes {
				list nodes {
					uses network-node;
				}
			}
			case links {
				list links {
					uses network-link;
				}
			}
			case prefixes {
				list prefixes {
					uses network-prefix;
				}
			}
		}
	}
}
