module odl-bgp-evpn-cfg {
    yang-version 1;
    namespace "urn:opendaylight:params:xml:ns:yang:controller:bgp:evpn";
    prefix "bgp-evpn-cfg";

    import config { prefix config; revision-date 2013-04-05; }
    import odl-bgp-parser-spi-cfg { prefix bgpspi; revision-date 2013-11-15; }
    import odl-bgp-rib-spi-cfg { prefix ribspi; revision-date 2013-11-15; }

    organization "Cisco Systems, Inc.";

    contact "Claudio D. Gasparini <cgaspari@cisco.com>";

    description
        "This module contains the base YANG definitions for
         BGP Evpn extension.

        Copyright (c)2016 Cisco Systems, Inc. All rights reserved.;

        This program and the accompanying materials are made available
        under the terms of the Eclipse Public License v1.0 which
        accompanies this distribution, and is available at
        http://www.eclipse.org/legal/epl-v10.html";

    revision "2016-03-21" {
         description
             "Initial revision";
    }

    identity bgp-evpn {
        base config:module-type;
        config:provided-service bgpspi:extension;
        config:provided-service ribspi:extension;
        config:java-name-prefix Evpn;
    }

    augment "/config:modules/config:module/config:configuration" {
        case bgp-evpn {
            when "/config:modules/config:module/config:type = 'bgp-evpn'";
        }
    }
}
