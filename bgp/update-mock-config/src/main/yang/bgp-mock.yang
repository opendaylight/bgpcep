// vi: set smarttab et sw=4 tabstop=4:
module bgp-mock {
    yang-version 1;
    namespace "urn:opendaylight:params:xml:ns:yang:controller:bgp:mock";
    prefix "th-java";

    import config { prefix config; revision-date 2013-04-05; }
    import threadpool { prefix th; revision-date 2013-04-09; }
    import bgp-listener { prefix bgpl; revision-date 2013-04-09; }


    organization "Cisco Systems, Inc.";

    contact "Robert Varga <rovarga@cisco.com>";

    description
        "This module contains the base YANG definitions for
         BGP message parser pure Java implementation.

        Copyright (c)2013 Cisco Systems, Inc. All rights reserved.;

        This program and the accompanying materials are made available
        under the terms of the Eclipse Public License v1.0 which
        accompanies this distribution, and is available at
        http://www.eclipse.org/legal/epl-v10.html";

    revision "2013-04-09" {
        description
            "Initial version.";
    }

    identity bgp-mock {
        base config:module-type;
        config:provided-service bgpl:listener;
    }

    augment "/config:modules/config:module/config:configuration" {
        case bgp-mock {
            when "/config:modules/config:module/config:type = 'bgp-mock'";
            container eventBus {
                uses config:service-ref {
                    refine type {
                        mandatory true;
                        config:required-identity th:eventbus;
                    }
                }
            }

            leaf hexDump {
                type string;
            }

            leaf binDump {
                type binary;
            }
        }
    }
}
