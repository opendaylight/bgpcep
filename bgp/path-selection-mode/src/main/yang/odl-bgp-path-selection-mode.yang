// vi: set smarttab et sw=4 tabstop=4:
module odl-bgp-path-selection-mode {
    yang-version 1;
    namespace "urn:opendaylight:params:xml:ns:yang:controller:bgp:path:selection:mode";
    prefix "psm";

    import config { prefix config; revision-date 2013-04-05; }

    organization "Cisco Systems, Inc.";

    contact "Claudio D. Gasparini <cgaspari@cisco.com>";

    description
        "This module contains the base YANG definitions for
         BGP Best path selection mode.

        Copyright (c)2016 Cisco Systems, Inc. All rights reserved.;

        This program and the accompanying materials are made available
        under the terms of the Eclipse Public License v1.0 which
        accompanies this distribution, and is available at
        http://www.eclipse.org/legal/epl-v10.html";

    revision "2016-03-01" {
         description
             "Initial revision";
    }

    identity path-selection-mode-factory {
        description
            "Service representing a path selection mode.";

        base "config:service-type";
        config:java-class "org.opendaylight.protocol.bgp.mode.api.PathSelectionMode";
    }

    identity advertise-n-paths {
         base config:module-type;
         config:provided-service path-selection-mode-factory;
         config:java-name-prefix AdvertiseNPaths;
    }

    augment "/config:modules/config:module/config:configuration" {
        case advertise-n-paths {
            when "/config:modules/config:module/config:type = 'advertise-n-paths'";
            leaf n-best-paths {
                description "Expected n best path selection.";
                type uint32;
                default 2;
            }
        }
    }

    identity advertise-all-paths {
         base config:module-type;
         config:provided-service path-selection-mode-factory;
         config:java-name-prefix AdvertiseAllPaths;
    }

    augment "/config:modules/config:module/config:configuration" {
        case advertise-all-paths {
            when "/config:modules/config:module/config:type = 'advertise-all-paths'";
        }
    }
}
