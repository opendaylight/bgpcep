module bgp-epe {
    yang-version 1;
    namespace "urn:opendaylight:params:xml:ns:yang:bgp-epe";
    prefix "bgp-epe";

    import ietf-inet-types { prefix inet; revision-date 2010-09-24; }

    organization "Cisco Systems, Inc.";
    contact "Milos Fabian <milfabia@cisco.com>";

    description
        "This module contains the base data concepts contained
        in draft-ietf-idr-bgpls-segment-routing-epe-00.

        Copyright (c)2015 Cisco Systems, Inc. All rights reserved.

        This program and the accompanying materials are made available
        under the terms of the Eclipse Public License v1.0 which
        accompanies this distribution, and is available at
        http://www.eclipse.org/legal/epl-v10.html";

    revision "2015-06-22" {
        description
            "Initial revision.";
    }

    grouping epe-node-descriptors {
        reference "https://tools.ietf.org/html/draft-ietf-idr-bgpls-segment-routing-epe-05#section-4.1";
        leaf bgp-router-id {
            description "BGP Router Identifier.";
            type inet:ipv4-address;
        }

        leaf member-asn {
            description "Confederation Member ASN.";
            type inet:as-number;
        }
    }
}
