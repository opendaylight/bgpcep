// vi: set smarttab et sw=4 tabstop=4:
module odl-bgp-linkstate-cfg {
    yang-version 1;
    namespace "urn:opendaylight:params:xml:ns:yang:controller:bgp:linkstate";
    prefix "bgpls";

    import config { prefix config; revision-date 2013-04-05; }
    import odl-bgp-parser-spi-cfg { prefix bgpspi; revision-date 2013-11-15; }
    import odl-bgp-rib-spi-cfg { prefix ribspi; revision-date 2013-11-15; }
    import odl-rsvp-parser-spi-cfg { prefix rsvp-spi; revision-date 2015-08-26; }

    organization "Cisco Systems, Inc.";

    contact "Robert Varga <rovarga@cisco.com>";

    description
        "This module contains the base YANG definitions for
         BGP Linkstate extension.

        Copyright (c)2013 Cisco Systems, Inc. All rights reserved.;

        This program and the accompanying materials are made available
        under the terms of the Eclipse Public License v1.0 which
        accompanies this distribution, and is available at
        http://www.eclipse.org/legal/epl-v10.html";

    revision "2015-08-26" {
        description
            "Add rsvp-extensions";
    }

    revision "2013-11-15" {
        description
            "Initial revision";
    }

    identity bgp-linkstate {
        base config:module-type;
        config:provided-service bgpspi:extension;
        config:provided-service ribspi:extension;
        config:java-name-prefix Linkstate;
    }

    augment "/config:modules/config:module/config:configuration" {
        case bgp-linkstate {
            when "/config:modules/config:module/config:type = 'bgp-linkstate'";

            leaf iana-linkstate-attribute-type {
                description "If true (default) linkstate attribute type (=29) allocated by IANA is used,
                    else type (=99) is used for parsing/serialization";
                type boolean;
                default true;
            }

            container rsvp-extensions {
                uses config:service-ref {
                    refine type {
                        mandatory true;
                        config:required-identity rsvp-spi:consumer-extensions;
                    }
                }
            }
        }
    }
}
