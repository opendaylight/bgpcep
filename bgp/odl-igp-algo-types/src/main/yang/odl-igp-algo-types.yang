module odl-igp-algo-types {
  yang-version 1;
  namespace "urn:opendaylight:yang:igp:algo:types";
  prefix "oiat";

  description
    "YANG model of IGP Algorithm Types IANA registry.

     Copyright (c) 2026 PANTHEON.tech, s.r.o. and others.  All rights reserved.

     This program and the accompanying materials are made available under the
     terms of the Eclipse Public License v1.0 which accompanies this distribution,
     and is available at http://www.eclipse.org/legal/epl-v10.html";

  revision "2026-11-10" {
    description
      "Initial revision";
  }

  // TODO: https://datatracker.ietf.org/doc/html/draft-ietf-lsr-ospf-flex-algo-yang-16/
  typedef named-algo {
    type enumeration {
      enum spf {
        value 0;
        description
          "Shortest Path First (SPF) algorithm based on link metric.
          This is the standard shortest path algorithm as computed by
          the IGP protocol. Consistent with the deployed practice for
          link-state protocols, Algorithm 0 permits any node to
          overwrite the SPF path with a different path based on its
          local policy.";
        reference
          "RFC 8665: OSPF Extensions for Segment Routing";
      }

      enum strict-spf {
        value 1;
        description
          "Strict Shortest Path First (SPF) algorithm based on
          link metric. The algorithm is identical to Algorithm 0 but
          Algorithm 1 requires that all nodes along the path will
          honor the SPF routing decision. Local policy at the node
          claiming support for Algorithm 1 MUST NOT alter the SPF
          paths computed by Algorithm 1.";
        reference
          "RFC 8665: OSPF Extensions for Segment Routing";
      }
    }
  }

  typedef flex-algo {
    type uint8 {
      range 128..255;
    }
    description
      "IGP Flexible Algorithm Type in IANA IGP Algorithm Types registry";
    reference
      "RFC 9350: IGP Flexible Algorithm";
  }

  typedef algo-type {
    type union {
      type named-algo;
      type flex-algo;
    }
    description
      "IGP Algorithm Type";
    reference
      "https://www.iana.org/assignments/igp-parameters#igp-algorithm-types";
  }
}
