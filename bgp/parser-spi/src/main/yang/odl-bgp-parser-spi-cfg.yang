// vi: set smarttab et sw=4 tabstop=4:
module odl-bgp-parser-spi-cfg {
    yang-version 1;
    namespace "urn:opendaylight:params:xml:ns:yang:controller:bgp:parser:spi";
    prefix "bgpspi";

    import config { prefix config; revision-date 2013-04-05; }

    organization "Cisco Systems, Inc.";

    contact "Robert Varga <rovarga@cisco.com>";

    description
        "This module contains the base YANG definitions for
         BGP listener service.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity consumer-extensions {
        description
            "Service representing a BGP parser extension registry. Extension
            consumers have this service injected.";

        base "config:service-type";
        config:java-class "org.opendaylight.protocol.bgp.parser.spi.BGPExtensionConsumerContext";
    }

    identity extensions {
        description
            "Service representing a BGP parser extension registry. Extension
            providers have this service injected for registration.";

        base "consumer-extensions";
        config:java-class "org.opendaylight.protocol.bgp.parser.spi.BGPExtensionProviderContext";
    }

    identity extension {
        description
            "Service representing a BGP parser extension.";

        base "config:service-type";
        config:java-class "org.opendaylight.protocol.bgp.parser.spi.BGPExtensionProviderActivator";
        config:disable-osgi-service-registration;
    }

    identity bgp-extensions-impl {
        base config:module-type;
        config:provided-service extensions;
        config:java-name-prefix SimpleBGPExtensionProviderContext;
    }

    augment "/config:modules/config:module/config:configuration" {
        case bgp-extensions-impl {
            when "/config:modules/config:module/config:type = 'bgp-extensions-impl'";

            list extension {
                uses config:service-ref {
                    refine type {
                        mandatory true;
                        config:required-identity extension;
                    }
                }
            }
        }
    }
}
