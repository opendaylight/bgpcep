// vi: set smarttab et sw=4 tabstop=4:
module odl-bgp-flowspec-cfg {
    yang-version 1;
    namespace "urn:opendaylight:params:xml:ns:yang:controller:bgp:flowspec";
    prefix "bgpfs";

    import config { prefix config; revision-date 2013-04-05; }
    import odl-bgp-parser-spi-cfg { prefix bgpspi; revision-date 2013-11-15; }
    import odl-bgp-rib-spi-cfg { prefix ribspi; revision-date 2013-11-15; }

    organization "Cisco Systems, Inc.";

    contact "Dana Kutenicsova <dkutenic@cisco.com>";

    description
        "This module contains the base YANG definitions for
         BGP Flowspec extension.

        Copyright (c)2015 Cisco Systems, Inc. All rights reserved.;

        This program and the accompanying materials are made available
        under the terms of the Eclipse Public License v1.0 which
        accompanies this distribution, and is available at
        http://www.eclipse.org/legal/epl-v10.html";

    revision "2015-04-23" {
        description
            "Initial revision";
    }

    identity bgp-flowspec {
        base config:module-type;
        config:provided-service bgpspi:extension;
        config:provided-service ribspi:extension;
        config:java-name-prefix Flowspec;
    }

    augment "/config:modules/config:module/config:configuration" {
        case bgp-flowspec {
            when "/config:modules/config:module/config:type = 'bgp-flowspec'";
        }
    }
}
