// vi: set smarttab et sw=4 tabstop=4:
module odl-bgp-topology-config {
    yang-version 1;
    namespace "urn:opendaylight:params:xml:ns:yang:odl-bgp-topology-config";
    prefix "bgp-topo-cfg";

    import network-topology { prefix nt; revision-date 2013-10-21; }
    import bgp-rib { prefix rib; }
    import odl-bgp-topology-types { prefix topology-tpes; revision-date 2016-05-24; }

    organization "Cisco Systems, Inc.";

    contact "Milos Fabian <milfabia@cisco.com>";

    description
        "This module contains the base YANG definitions for
         BGP topology provider configuration.

        Copyright (c)2016 Cisco Systems, Inc. All rights reserved.;

        This program and the accompanying materials are made available
        under the terms of the Eclipse Public License v1.0 which
        accompanies this distribution, and is available at
        http://www.eclipse.org/legal/epl-v10.html";

    revision "2018-03-29" {
        description "Add support for add-path for all afi/safi.";
    }

    revision "2017-12-07" {
        description "Add support for add-path in base BGP NLRI.";
    }

    revision "2016-07-26" {
        description
            "Initial revision";
    }

    grouping bgp-topology-configuration {
        leaf rib-id {
            type rib:rib-id;
        }
    }

    augment "/nt:network-topology/nt:topology" {
        when "/nt:network-topology/nt:topology/nt:topology-types/topology-tpes:bgp-ipv4-reachability-topology or"
            + "/nt:network-topology/nt:topology/nt:topology-types/topology-tpes:bgp-ipv6-reachability-topology or"
            + "/nt:network-topology/nt:topology/nt:topology-types/topology-tpes:bgp-linkstate-topology";
        uses bgp-topology-configuration;
    }
}
