// vi: set smarttab et sw=4 tabstop=4:
module odl-bgp-reachability-ipv6-cfg {
    yang-version 1;
    namespace "urn:opendaylight:params:xml:ns:yang:controller:bgp:reachability:ipv6";
    prefix "bgptopo";

    import config { prefix config; revision-date 2013-04-05; }
    import network-topology { prefix nt; revision-date 2013-10-21; }
    import odl-bgp-rib-cfg { prefix ribapi; revision-date 2013-07-01; }
    import odl-topology-api-cfg { prefix topo; revision-date 2013-11-15; }
    import opendaylight-md-sal-binding { prefix mdsal; revision-date 2013-10-28; }

    organization "Cisco Systems, Inc.";

    contact "Robert Varga <rovarga@cisco.com>";

    description
        "This module contains the base YANG definitions for
         BGP topology provider.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

 identity bgp-reachability-ipv6 {
        base config:module-type;
        config:provided-service topo:topology-reference;
        config:java-name-prefix Ipv6ReachabilityTopologyBuilder;
    }

    augment "/config:modules/config:module/config:configuration" {
        case bgp-reachability-ipv6 {
            when "/config:modules/config:module/config:type = 'bgp-reachability-ipv6'";

            container data-provider {
                uses config:service-ref {
                    refine type {
                        mandatory true;
                        config:required-identity mdsal:binding-async-data-broker;
                    }
                }
            }

            container local-rib {
                uses config:service-ref {
                    refine type {
                        mandatory true;
                        config:required-identity ribapi:rib;
                    }
                }
            }

            leaf topology-id {
                type nt:topology-id;
                mandatory true;
            }
        }
    }

}
