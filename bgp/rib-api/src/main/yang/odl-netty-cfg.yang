// Contents of "odl-netty-cfg"
module odl-netty-cfg {
    yang-version 1;
    namespace "urn:opendaylight:params:xml:ns:yang:controller:netty:cfg";
    prefix "nettykey";

    organization "AT&T Services, Inc.";

    contact "Om Prakash <op317q@att.com>";

    description
        "This module contains the base YANG definitions for
         Netty Epoll Signature option.

        Copyright (c)2016 AT&T Services, Inc. All rights reserved.;

        This program and the accompanying materials are made available
        under the terms of the Eclipse Public License v1.0 which
        accompanies this distribution, and is available at
        http://www.eclipse.org/legal/epl-v10.html";

    revision "2016-03-24" {
        description
            "Initial revision";
    }


    typedef rfc2385-key {
        type string {
            length 1..80;
        }
    }

}
