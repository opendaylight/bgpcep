module bgp-rib-rpc {
    namespace "urn:opendaylight:params:xml:ns:yang:bgp-rib-rpc";
    prefix "bgp-rpc";

    import bgp-multiprotocol { prefix bgp-mp; revision-date 2013-09-19; }
    import bgp-rib { prefix rib; revision-date 2013-09-25; }
    import yang-ext { prefix ext; revision-date "2013-07-09"; }

    organization "Cisco Systems, Inc.";
    contact "Iveta Halanova <ihalanov@cisco.com>";

    description
        "Module contains rpc for route refresh request, which is described in rfc2918.

        Copyright (c) 2016 Cisco Systems, Inc. All rights reserved.

        This program and the accompanying materials are made available
        under the terms of the Eclipse Public License v1.0 which
        accompanies this distribution, and is available at
        http://www.eclipse.org/legal/epl-v10.html";

    revision 2016-03-22 {
        description "Initial revision";
    }

    identity peer-context {
        description "Identity used to mark the Peer context for binding RPCs in a particular RIB.";
    }

    typedef peer-ref {
        type instance-identifier;
        ext:context-reference "peer-context";
    }

    grouping peer-reference {
        leaf peer-ref {
            type peer-ref;
            mandatory true;
            ext:context-reference "peer-context";
        }
    }

    grouping rr-msg-args {
        uses peer-reference;
        uses bgp-mp:bgp-table-type;
    }

    rpc route-refresh-request {
        input {
            uses rr-msg-args;
        }
    }

    augment "/rib:bgp-rib/rib:rib/rib:peer" {
        ext:context-instance "peer-context";
    }
}
