// Contents of "odl-bgp-benchmark"
module odl-bgp-app-peer-benchmark {
    namespace "urn:opendaylight:params:xml:ns:yang:odl-bgp-app-peer-benchmark";
    prefix "bgp-app-peer-bm";

    import ietf-inet-types { prefix inet; revision-date 2013-07-15; }

    organization "Cisco Systems, Inc.";
    contact "Milos Fabian <milfabia@cisco.com>";

    description
        "This module contains Yang Data Models for BGP Application Peer
        Benchmark application.

        Copyright (c)2016 Cisco Systems, Inc. All rights reserved.

        This program and the accompanying materials are made available
        under the terms of the Eclipse Public License v1.0 which
        accompanies this distribution, and is available at
        http://www.eclipse.org/legal/epl-v10.html";

    revision 2020-01-20 {
        description "Update to use -no-zone-adresses";
    }

    revision 2016-03-09 {
        description "Initial revision";
    }

    grouping input {
        leaf prefix {
            mandatory true;
            type inet:ipv4-prefix;
            description
                "IPv4 prefix";
        }
        leaf count {
            mandatory true;
            type uint32;
            description
                "loop count";
        }
        leaf batchsize {
            mandatory true;
            type uint32;
            description
                "batchsize";
        }
    }

    grouping output {
        container result {
            leaf count {
                mandatory true;
                type uint32;
            }
            leaf duration {
                mandatory true;
                type uint32;
                units seconds;
            }
            leaf rate {
                mandatory true;
                type uint32;
                units "per-second";
            }
        }
    }

    rpc add-prefix {
        description
                "Add prefix into RIB";
        input {
            uses input;
            leaf nexthop {
                mandatory true;
                type inet:ipv4-address-no-zone;
                description
                    "nexthop";
            }
        }

        output {
            uses output;
        }
    }

    rpc delete-prefix {
        description
            "Delete prefix into RIB";

        input {
            uses input;
        }

        output {
            uses output;
        }
    }

}
