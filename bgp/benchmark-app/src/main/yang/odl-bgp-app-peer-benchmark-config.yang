module odl-bgp-app-peer-benchmark-config {
    yang-version 1;
    namespace "urn:opendaylight:params:xml:ns:yang:odl-bgp-app-peer-benchmark-config";
    prefix bgp-benchmark-app-config;

    description
        "This module contains the base YANG definitions for
         BGP Peer Acceptor Configuration.
         Copyright (c)2016 Cisco Systems, Inc. All rights reserved.;

         This program and the accompanying materials are made available
         under the terms of the Eclipse Public License v1.0 which
         accompanies this distribution, and is available at
         http://www.eclipse.org/legal/epl-v10.html";

    revision "2016-11-29" {
        description
            "Initial revision.";
    }

    container config {
        leaf app-peer-id {
            type string;
            default "192.0.2.6";
            mandatory true;
        }
    }
}
