// Contents of "odl-bgp-benchmark-cfg"
module odl-bgp-benchmark-cfg {
    namespace "urn:opendaylight:params:xml:ns:yang:controller:odl-bgp-benchmark-cfg";
    prefix "bgp-bm-cfg";

    import config { prefix config; revision-date 2013-04-05; }
    import opendaylight-md-sal-binding { prefix mdsal; revision-date 2013-10-28; }

    organization "Cisco Systems, Inc.";
    contact "Milos Fabian <milfabia@cisco.com>";

    description
        "This module contains Configuration Yang Data Model for BGP Benchmark application.

        Copyright (c)2016 Cisco Systems, Inc. All rights reserved.

        This program and the accompanying materials are made available
        under the terms of the Eclipse Public License v1.0 which
        accompanies this distribution, and is available at
        http://www.eclipse.org/legal/epl-v10.html";

    revision 2016-03-09 {
        description "Initial revision";
    }

    identity app-peer-benchmark {
        base config:module-type;
        config:java-name-prefix AppPeerBenchmark;
    }

    augment "/config:modules/config:module/config:configuration" {
        case app-peer-benchmark {
            when "/config:modules/config:module/config:type = 'app-peer-benchmark'";

            container rpc-registry {
                uses config:service-ref {
                    refine type {
                        mandatory true;
                        config:required-identity mdsal:binding-rpc-registry;
                    }
                }
            }

            container binding-data-broker {
                uses config:service-ref {
                    refine type {
                        mandatory true;
                        config:required-identity mdsal:binding-async-data-broker;
                    }
                }
            }

            leaf app-rib-id {
                type string;
                default "example-app-rib";
            }

        }
    }

}
