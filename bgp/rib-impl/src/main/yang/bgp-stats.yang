module bgp-stats {
    namespace "urn:opendaylight:params:xml:ns:yang:controller:bgp:stats";
    prefix "bgp-stats";

    import ietf-yang-types { prefix yang; revision-date 2013-07-15; }

    organization "Brocade Communications Systems, Inc.";
    contact "Kevin Wang <kwang@brocade.com>";

    description
        "This module contains the base data model of BGP statistic.

        Copyright (c) 2016 Brocade Communications Systems, Inc. All rights reserved.

        This program and the accompanying materials are made available
        under the terms of the Eclipse Public License v1.0 which
        accompanies this distribution, and is available at
        http://www.eclipse.org/legal/epl-v10.html";

    revision 2016-06-06 {
        description "Initial revision";
    }

    grouping bgp-message-state {
        leaf count {
            description "Total number of BGP messages.";
            type yang:zero-based-counter32;
        }

        leaf timestamp {
            description "The BGP message timestamp (seconds).";
            type yang:timestamp;
        }
    }

    grouping bgp-message-stats {
        container received {
            description "The received BGP messages statistics.";
            uses bgp-message-state;
        }

        container sent {
            description "The sent BGP messages statistics.";
            uses bgp-message-state;
        }
    }

    grouping bgp-error {
        leaf code {
            description "The BGP error code.";
            type uint8;
            default 0;
        }

        leaf sub-code {
            description "The BGP error sub-code.";
            type uint8;
            default 0;
        }
    }
}
