module bgp-stats-rib-impl {
    namespace "urn:opendaylight:params:xml:ns:yang:controller:bgp:stats:rib:impl";
    prefix "bgp-stats-rib-impl";

    import bgp-rib-impl { prefix rib-impl; revision-date 2016-06-06; }
    import bgp-multiprotocol { prefix bgp-mp; revision-date 2013-09-19; }
    import ietf-yang-types { prefix yang; revision-date 2013-07-15; }

    organization "Brocade Communications Systems, Inc.";
    contact "Kevin Wang <kwang@brocade.com>";

    description
        "This module contains the base data model of BGP render statistic.

        Copyright (c) 2016 Brocade Communications Systems, Inc. All rights reserved.

        This program and the accompanying materials are made available
        under the terms of the Eclipse Public License v1.0 which
        accompanies this distribution, and is available at
        http://www.eclipse.org/legal/epl-v10.html";

    revision 2016-06-06 {
        description "Initial revision";
    }

    grouping bgp-render-stats {
        container bgp-render-state {
            uses rib-impl:bgp-rib-impl-identifiers;

            leaf configured-peer-count {
                description "The total number of BGP peer configured to be associated with this RIB instance.";
                type yang:zero-based-counter32;
            }

            leaf connected-peer-count {
                description "The total number of BGP peer connected to this RIB instance.";
                type yang:zero-based-counter32;
            }

            leaf loc-rib-routes-count {
                description "The total number of routes in loc-rib.";
                type yang:zero-based-counter32;
            }

            list loc-rib-route-table {
                key "afi safi";
                uses bgp-mp:bgp-table-type;

                leaf routes-count {
                    description "The total number of routes in table.";
                    type yang:zero-based-counter32;
                }
            }
        }
    }
}
