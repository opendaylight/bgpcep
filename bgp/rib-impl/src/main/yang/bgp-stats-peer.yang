module bgp-stats-peer {
    namespace "urn:opendaylight:params:xml:ns:yang:controller:bgp:stats:peer";
    prefix "bgp-stats-peer";

    import bgp-peer { prefix peer; revision-date 2016-06-06; }
    import bgp-multiprotocol { prefix bgp-mp; revision-date 2013-09-19; }
    import bgp-message { prefix bgp-msg; revision-date 2013-09-19; }
    import ietf-yang-types { prefix yang; revision-date 2013-07-15; }

    organization "Brocade Communications Systems, Inc.";
    contact "Kevin Wang <kwang@brocade.com>";

    description
        "This module contains the base data model of BGP peer statistic.

        Copyright (c) 2016 Brocade Communications Systems, Inc. All rights reserved.

        This program and the accompanying materials are made available
        under the terms of the Eclipse Public License v1.0 which
        accompanies this distribution, and is available at
        http://www.eclipse.org/legal/epl-v10.html";

    revision 2016-06-06 {
        description "Initial revision";
    }

    grouping bgp-message-state {
        leaf count {
            description "Total number of BGP messages.";
            type yang:zero-based-counter32;
        }

        leaf timestamp {
            description "The BGP message timestamp (seconds).";
            type yang:timestamp;
        }
    }

    grouping bgp-message-stats {
        container received {
            description "The received BGP messages statistics.";
            uses bgp-message-state;
        }

        container sent {
            description "The sent BGP messages statistics.";
            uses bgp-message-state;
        }
    }

    grouping bgp-peer-state {
        container bgp-peer-state {
            list route-table {
                key "afi safi";
                uses bgp-mp:bgp-table-type;

                leaf adj-rib-in-routes-count {
                    description "The total number of Adj-RIB-In routes in table.";
                    type yang:zero-based-counter32;
                }

                leaf adj-rib-out-routes-count {
                    description "The total number of Adj-RIB-Out routes in table.";
                    type yang:zero-based-counter32;
                }

                leaf effective-rib-in-routes-count {
                    description "The total number of Effective-RIB-In routes in table.";
                    type yang:zero-based-counter32;
                }
            }

            leaf session-established-count {
                description "The total number of time the BGP session was transitioned to Up state.";
                type yang:zero-based-counter32;
            }
        }
    }

    grouping bgp-session-state {
        container bgp-session-state {

            leaf session-state {
                description "The BGP peer connection state.";
                type string;
            }

            leaf session-duration {
                description "The session duration (time formated d:HH:mm:ss).";
                type string;
            }

            leaf holdtime-current {
                description "Time interval (in seconds) for HoldTimer established with the peer.";
                type uint16;
                default 0;
            }

            leaf keepalive-current {
                description "Time interval (in seconds) for KeepAlive established with the peer.";
                type uint16;
                default 0;
            }

            container remote-peer-preferences {
                description "The BGP remote peer preferences, to which this BGP peer is connected.";
                uses peer:bgp-peer-preferences;
            }

            container local-peer-preferences {
                description "The BGP local peer preferences.";
                uses peer:bgp-peer-preferences;
            }

            container messages-stats {
                description "The BGP messages statistics.";
                container total-msgs {
                    description "The statistics for all received/sent BGP messages.";
                    uses bgp-message-stats;
                }

                container keep-alive-msgs {
                    description "The statistics for received/sent BGP Keep-Alive messages.";
                    uses bgp-message-stats;
                }

                container update-msgs {
                    description "The statistics for received/sent BGP Update messages.";
                    uses bgp-message-stats;
                }

                container route-refresh-msgs {
                    description "The statistics for received/sent BGP Route Refresh messages.";
                    uses bgp-message-stats;
                }

                container error-msgs {
                    container error-received-total {
                        description "The total number of received BGP Error (notification) messages.";
                        uses bgp-message-state;
                    }

                    list error-received {
                        description "The received BGP Error (notification) messages.";
                        key "error-code error-subcode";

                        uses bgp-message-state;
                        uses bgp-msg:notify-message;
                    }

                    container error-sent-total {
                        description "The total number of sent BGP Error (notification) messages.";
                        uses bgp-message-state;
                    }

                    list error-sent {
                        description "The sent BGP Error (notification) messages.";
                        key "error-code error-subcode";

                        uses bgp-message-state;
                        uses bgp-msg:notify-message;
                    }
                }
            }
        }
    }

    grouping bgp-peer-stats {
        uses bgp-peer-state;
        uses bgp-session-state;
    }
}
