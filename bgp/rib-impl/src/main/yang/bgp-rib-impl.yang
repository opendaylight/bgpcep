module bgp-rib-impl {
    namespace "urn:opendaylight:params:xml:ns:yang:controller:bgp:rib:impl:config";
    prefix "bgp-rib-impl";

    import bgp-types { prefix bgp-t; revision-date 2013-09-19; }
    import bgp-rib { prefix rib; revision-date 2013-09-25; }
    import ietf-inet-types { prefix inet; revision-date 2013-07-15; }
    import opendaylight-md-sal-binding {prefix mdsb; revision-date 2013-10-28; }

    organization "Brocade Communications Systems, Inc.";
    contact "Kevin Wang <kwang@brocade.com>";

    description
        "This module contains the base data model of BGP RIB implementation.

        Copyright (c) 2016 Brocade Communications Systems, Inc. All rights reserved.

        This program and the accompanying materials are made available
        under the terms of the Eclipse Public License v1.0 which
        accompanies this distribution, and is available at
        http://www.eclipse.org/legal/epl-v10.html";

    revision 2016-06-06 {
        description "Initial revision";
    }

    grouping bgp-rib-impl-identifiers {
        leaf local-as {
            description "Our local AS number. Needed by best selection path attribute.";
            type inet:as-number;
            mandatory true;
        }

        leaf bgp-rib-id {
            description "Our local BGP identifier. Needed by best selection path attribute.";
            mandatory true;
            type bgp-t:bgp-id;
        }

        leaf rib-id {
            description "Identifier of this RIB in local data store.";
            type rib:rib-id;
            mandatory true;
        }

        leaf cluster-id {
            description "IBGP identifier. Needed by route reflection.";
            reference "https://tools.ietf.org/html/rfc4456#section-7";
            type bgp-t:cluster-identifier;
        }

        leaf read-only-limit {
            description "Peers time limit for been on Read Only status";
            type uint16;
            default 120;
        }
    }
}
