module bgp-vpn-ipv4 {
    namespace "urn:opendaylight:params:xml:ns:yang:bgp-vpn-ipv4";
    prefix "bgp-vpn-ipv4";

    import bgp-message { prefix bgp-msg; revision-date 2017-12-07; }
    import bgp-multiprotocol { prefix bgp-mp; revision-date 2017-12-07; }
    import bmp-monitor { prefix bmp-mon; revision-date 2018-03-29; }
    import bgp-rib { prefix bgp-rib; revision-date 2018-03-29; }
    import bgp-vpn { prefix bgp-vpn; revision-date 2018-03-29; }

    organization "Cisco Systems, Inc.";
    contact "Iveta Halanova <ihalanov@cisco.com>";

    description
        "This module contains the base data model of a BGP message.
        It rolls up the definitions contained in RFC4364.

        Copyright (c)2016 Cisco Systems, Inc. All rights reserved.

        This program and the accompanying materials are made available
        under the terms of the Eclipse Public License v1.0 which
        accompanies this distribution, and is available at
        http://www.eclipse.org/legal/epl-v10.html";

    revision "2018-03-29" {
        description "Add support for add-path for all afi/safi.";
    }

    revision "2017-12-07" {
        description "Add support for add-path in base BGP NLRI.";
    }

    revision 2016-02-10 {
        reference "https://tools.ietf.org/html/rfc4364";
        description "Initial revision";
    }

    grouping l3vpn-ipv4-routes {
        container vpn-ipv4-routes {
            uses bgp-vpn:l3vpn-ip-route;
        }
    }

    grouping l3vpn-ipv4-destination {
        container vpn-ipv4-destination {
            uses bgp-vpn:l3vpn-ip-destination-type;
        }
    }

    augment "/bgp-msg:update/bgp-msg:attributes/bgp-mp:mp-reach-nlri/bgp-mp:advertized-routes/bgp-mp:destination-type" {
        case destination-vpn-ipv4-case {
            uses l3vpn-ipv4-destination;
        }
    }

    augment "/bgp-msg:update/bgp-msg:attributes/bgp-mp:mp-unreach-nlri/bgp-mp:withdrawn-routes/bgp-mp:destination-type" {
        case destination-vpn-ipv4-case {
            uses l3vpn-ipv4-destination;
        }
    }

    augment "/bgp-rib:application-rib/bgp-rib:tables/bgp-rib:routes" {
        case vpn-ipv4-routes-case {
            uses l3vpn-ipv4-routes;
        }
    }

    augment "/bgp-rib:bgp-rib/bgp-rib:rib/bgp-rib:loc-rib/bgp-rib:tables/bgp-rib:routes" {
        case vpn-ipv4-routes-case {
            uses l3vpn-ipv4-routes;
        }
    }

    augment "/bgp-rib:bgp-rib/bgp-rib:rib/bgp-rib:peer/bgp-rib:adj-rib-in/bgp-rib:tables/bgp-rib:routes" {
        case vpn-ipv4-routes-case {
            uses l3vpn-ipv4-routes;
        }
    }

    augment "/bgp-rib:bgp-rib/bgp-rib:rib/bgp-rib:peer/bgp-rib:effective-rib-in/bgp-rib:tables/bgp-rib:routes" {
        case vpn-ipv4-routes-case {
            uses l3vpn-ipv4-routes;
        }
    }

    augment "/bgp-rib:bgp-rib/bgp-rib:rib/bgp-rib:peer/bgp-rib:adj-rib-out/bgp-rib:tables/bgp-rib:routes" {
        case vpn-ipv4-routes-case {
            uses l3vpn-ipv4-routes;
        }
    }

    augment "/bmp-mon:bmp-monitor/bmp-mon:monitor/bmp-mon:router/bmp-mon:peer/bmp-mon:pre-policy-rib/bmp-mon:tables/bmp-mon:routes" {
        case vpn-ipv4-routes-case {
            uses l3vpn-ipv4-routes;
        }
    }

    augment "/bmp-mon:bmp-monitor/bmp-mon:monitor/bmp-mon:router/bmp-mon:peer/bmp-mon:post-policy-rib/bmp-mon:tables/bmp-mon:routes" {
        case vpn-ipv4-routes-case {
            uses l3vpn-ipv4-routes;
        }
    }
}
