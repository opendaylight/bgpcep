module odl-bgp-vpn-ipv6-cfg {
    namespace "urn:opendaylight:params:xml:ns:yang:controller:bgp:vpn:ipv6";
    prefix "bgp-vpn-cfg";

    import config { prefix config; revision-date 2013-04-05; }
    import odl-bgp-parser-spi-cfg { prefix bgpspi; revision-date 2013-11-15; }
    import odl-bgp-rib-spi-cfg { prefix ribspi; revision-date 2013-11-15; }

    organization "Brocade Communications Systems, Inc.";
    contact "Kevin Wang <kwang@brocade.com>";

    description
        "This module contains the base YANG definitions for
         BGP-MPLS IPv6 VPN extension.

        Copyright (c) 2016 Brocade Communications Systems, Inc. All rights reserved.;

        This program and the accompanying materials are made available
        under the terms of the Eclipse Public License v1.0 which
        accompanies this distribution, and is available at
        http://www.eclipse.org/legal/epl-v10.html";

    revision "2016-03-31" {
        description
            "Initial revision";
    }

    identity bgp-vpn-ipv6 {
        base config:module-type;
        config:provided-service bgpspi:extension;
        config:provided-service ribspi:extension;
        config:java-name-prefix VpnIpv6;
    }

    augment "/config:modules/config:module/config:configuration" {
        case bgp-vpn-ipv6 {
            when "/config:modules/config:module/config:type = 'bgp-vpn-ipv6'";
        }
    }
}
