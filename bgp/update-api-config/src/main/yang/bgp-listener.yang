// vi: set smarttab et sw=4 tabstop=4:
module bgp-listener {
    yang-version 1;
    namespace "urn:opendaylight:params:xml:ns:yang:controller:bgp:listener";
    prefix "bgpl";

    import config { prefix config; revision-date 2013-04-05; }

    organization "Cisco Systems, Inc.";

    contact "Robert Varga <rovarga@cisco.com>";

    description
        "This module contains the base YANG definitions for
         BGP listener service.

        Copyright (c)2013 Cisco Systems, Inc. All rights reserved.;

        This program and the accompanying materials are made available
		under the terms of the Eclipse Public License v1.0 which
		accompanies this distribution, and is available at
		http://www.eclipse.org/legal/epl-v10.html";

    revision "2013-04-09" {
        description
            "Initial revision";
    }

    identity listener {
        description
            "Service representing a BGP service. Each instance allows
             registration of listeners. Each listener has its own BGP session.
             Events happening on the session are routed to the listener.";

        base "config:service-type";
        config:java-class "org.opendaylight.protocol.bgp.rib.impl.BGP";
    }
}
