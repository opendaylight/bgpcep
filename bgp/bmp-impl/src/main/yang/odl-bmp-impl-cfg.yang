module odl-bmp-impl-cfg {
    yang-version 1;
    namespace "urn:opendaylight:params:xml:ns:yang:controller:bmp:impl";
    prefix "bmp-impl";

    import config { prefix config; revision-date 2013-04-05; }
    import odl-bgp-rib-spi-cfg { prefix ribspi; revision-date 2013-11-15; }
    import netty { prefix netty; revision-date 2013-11-19; }
    import ietf-inet-types { prefix inet; revision-date 2013-07-15; }
    import opendaylight-md-sal-binding-v1-codec { prefix mdsb1; revision-date 2016-07-14; }
    import opendaylight-md-sal-dom {prefix sal; revision-date 2013-10-28; }
    import rfc2385 { prefix rfc2385; revision-date 2016-03-24; }

    organization "Cisco Systems, Inc.";

    contact "Milos Fabian <milfabia@cisco.com>";

    description
        "This module contains the base YANG definitions for
         BMP implementation.

        Copyright (c)2015 Cisco Systems, Inc. All rights reserved.;

        This program and the accompanying materials are made available
        under the terms of the Eclipse Public License v1.0 which
        accompanies this distribution, and is available at
        http://www.eclipse.org/legal/epl-v10.html";

    revision "2015-05-18" {
        description
            "Initial revision";
    }

    identity bmp-dispatcher {
        description
            "Service representing a BMP dispatcher service. The service
             can create both BMP client sessions and BMP servers.";

        base "config:service-type";
        config:java-class "org.opendaylight.protocol.bmp.api.BmpDispatcher";
        config:disable-osgi-service-registration;
    }

    identity bmp-dispatcher-impl {
        base config:module-type;
        config:provided-service bmp-dispatcher;
        config:java-name-prefix BmpDispatcherImpl;
    }

    augment "/config:modules/config:module/config:configuration" {
        case bmp-dispatcher-impl {
            when "/config:modules/config:module/config:type = 'bmp-dispatcher-impl'";
        }
    }

    identity bmp-monitor {
        description
            "Service representing a BMP monitoring service.";

        base "config:service-type";
        config:java-class "org.opendaylight.protocol.bmp.impl.spi.BmpMonitoringStation";
    }

    identity bmp-monitor-impl {
        base config:module-type;
        config:provided-service bmp-monitor;
        config:java-name-prefix BmpMonitorImpl;
    }

    augment "/config:modules/config:module/config:configuration" {
        case bmp-monitor-impl {
            when "/config:modules/config:module/config:type = 'bmp-monitor-impl'";

            container extensions {
                uses config:service-ref {
                    refine type {
                        mandatory true;
                        config:required-identity ribspi:consumer-extensions;
                    }
                }
            }

            container codec-tree-factory {
                uses config:service-ref {
                    refine type {
                        mandatory true;
                        config:required-identity mdsb1:binding-v1-codec-tree-factory;
                    }
                }
            }

            container dom-data-provider {
                uses config:service-ref {
                    refine type {
                        mandatory true;
                        config:required-identity sal:dom-async-data-broker;
                    }
                }
            }

            container bmp-dispatcher {
                uses config:service-ref {
                    refine type {
                        mandatory true;
                        config:required-identity bmp-dispatcher;
                    }
                }
            }

            leaf binding-address {
                type inet:ip-address;
                default "0.0.0.0";
            }

            leaf binding-port {
                type inet:port-number;
                mandatory true;
            }

            list monitored-router {
                leaf address {
                    type inet:ip-address;
                    mandatory true;
                }

                key "address";

                leaf active {
                    type boolean;
                    default false;
                }

                leaf port {
                    type inet:port-number;
                    mandatory false;
                }

                leaf password {
                    type rfc2385:rfc2385-key;
                    description "RFC2385 shared secret";
                }
            }
        }
    }
}
