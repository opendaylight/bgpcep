module odl-bmp-monitor-config {
    yang-version 1;
    namespace "urn:opendaylight:params:xml:ns:yang:bmp-monitor-config";
    prefix bmp-monitor-config;

    import ietf-inet-types { prefix inet; revision-date 2013-07-15; }
    import rfc2385 { prefix rfc2385; revision-date 2016-03-24; }
    import bmp-monitor { prefix bmp-monitor; revision-date 2015-05-12; }

    description
        "This module contains the base YANG definitions for
         BMP Monitor Configuration.
         Copyright (c) 2017 Pantheon Technologies s.r.o. and others.  All rights reserved.

         This program and the accompanying materials are made available
         under the terms of the Eclipse Public License v1.0 which
         accompanies this distribution, and is available at
         http://www.eclipse.org/legal/epl-v10.html";

    revision "2017-05-17" {
        description
            "Initial revision.";
    }

    container odl-bmp-monitors {
        list bmp-monitor-config {

            key "monitor-id";
            leaf monitor-id {
                type bmp-monitor:monitor-id;
            }

            leaf binding-address {
                type inet:ip-address;
                default "0.0.0.0";
            }

            leaf binding-port {
                type inet:port-number;
                mandatory true;
            }

            list monitored-router {
                leaf address {
                    type inet:ip-address;
                    mandatory true;
                }

                key "address";

                leaf active {
                    type boolean;
                    default false;
                }

                leaf port {
                    type inet:port-number;
                    mandatory false;
                }

                leaf password {
                    type rfc2385:rfc2385-key;
                    description "RFC2385 shared secret";
                }
            }
        }
    }

}
