module bgp-linkstate {
    yang-version 1;
    namespace "urn:opendaylight:params:xml:ns:yang:bgp-linkstate";
    prefix "bgp-ls";

    import ietf-inet-types { prefix inet; revision-date 2013-07-15; }
    import ietf-routing-types { prefix rt-types; }
    import bgp-message { prefix bgp-msg; revision-date 2020-01-20; }
    import bgp-multiprotocol { prefix bgp-mp; revision-date 2018-03-29; }
    import bgp-rib { prefix bgp-rib; revision-date 2018-03-29; }
    import bgp-types { prefix bgp-t; revision-date 2020-01-20; }
    import network-concepts { prefix netc; revision-date 2013-11-25; }
    import rsvp { prefix rsvp; revision-date 2015-08-20; }
    import bgp-segment-routing { prefix bgp-sr; revision-date 2024-12-19; }
    import bgp-epe { prefix bgp-epe; revision-date 2024-12-19; }
    import bmp-monitor { prefix bmp-mon; revision-date 2020-01-20; }

    organization "Cisco Systems, Inc.";
    contact "Dana Kutenicsova <dkutenic@cisco.com>";

    description
        "This module contains the base data model of a BGP message.
        It rolls up the definitions contained in RFC4271
        and RFC7752.

        Copyright (c)2013 Cisco Systems, Inc. All rights reserved.

        This program and the accompanying materials are made available
        under the terms of the Eclipse Public License v1.0 which
        accompanies this distribution, and is available at
        http://www.eclipse.org/legal/epl-v10.html";

    revision 2024-12-19 {
        description "Update to RFC9552 (BGP-LS), RFC9085 (SR), RFC9514 (SRv6), RFC9351 (Flex-Algo),
                     RFC9104 (Extended Admin Group), RFC8814 (MSD), RFC9086 (EPE) and RFC9294 (ASLA)";
        reference "https://www.iana.org/assignments/bgp-ls-parameters/bgp-ls-parameters.xhtml";
    }

    revision 2020-01-20 {
        description "Update to use -no-zone-adresses";
    }

    revision "2018-03-29" {
        description "Add support for add-path for all afi/safi.
            and Updated to include Performance Metric Extensions";
        reference "draft-ietf-idr-te-pm-bgp-17";
    }

    revision "2017-12-07" {
        description "Add support for add-path in base BGP NLRI.";
    }

    revision "2015-02-10" {
        description
            "Updated to include segment routing.";
    }

    revision "2013-11-25" {
        description
            "Updated to cover network-concepts.";
    }

    revision "2013-09-18" {
        description
            "Initial revision.";
        reference "draft-ietf-idr-ls-distribution-03";
    }

    // BGP Link State family definition

    identity linkstate-address-family {
        reference "https://www.rfc-editor.org/info/rfc9552/#section-5.2";
        base bgp-t:address-family;
    }

    identity linkstate-subsequent-address-family {
        reference "https://www.rfc-editor.org/info/rfc9552/#section-5.2";
        base bgp-t:subsequent-address-family;
    }

    // BGP Link State NLRI definitions

    typedef nlri-type {
        reference "https://www.rfc-editor.org/info/rfc9552/#section-5.2";
        type enumeration {
            enum node {
                value 1;
            }
            enum link {
                value 2;
            }
            enum ipv4-prefix {
                value 3;
            }
            enum ipv6-prefix {
                value 4;
            }
            enum sr-policy {
                reference "https://www.rfc-editor.org/info/rfc9857/#section-8.1";
                value 5;
            }
            enum srv6-sid {
                reference "https://www.rfc-editor.org/info/rfc9514/#section-6";
                value 6;
            }
        }
    }

    // TODO: is there a YANG projection of https://www.iana.org/assignments/bgp-ls-parameters#protocol-ids ?
    typedef protocol-id {
        reference "https://www.rfc-editor.org/info/rfc9552/#section-5.2";
        type enumeration {
            enum isis-level1 {
                value 1;
            }
            enum isis-level2 {
                value 2;
            }
            enum ospf {
                value 3;
            }
            enum direct {
                value 4;
            }
            enum static {
                value 5;
            }
            enum ospf-v3 {
                value 6;
            }
            enum bgp-epe {
                reference "https://www.rfc-editor.org/info/rfc9086/#section-4";
                value 7;
            }
            enum segment-routing {
                reference "https://www.rfc-editor.org/info/rfc9857/#section-8.2";
                value 9;
            }
        }
    }

    typedef ospf-route-type {
        reference "https://www.rfc-editor.org/info/rfc9552/#section-5.2.3.1";
        type enumeration {
            enum intra-area {
                value 1;
            }
            enum inter-area {
                value 2;
            }
            enum external1 {
                value 3;
            }
            enum external2 {
                value 4;
            }
            enum nssa1 {
                value 5;
            }
            enum nssa2 {
                value 6;
            }
        }
    }

    typedef identifier {
        reference "https://www.rfc-editor.org/info/rfc5307/#section-1.1";
        type uint64;
    }

    typedef domain-identifier {
        reference "https://www.rfc-editor.org/info/rfc9552/#section-5.2.1.4";
        type uint32;
    }

    typedef area-identifier {
        reference "https://www.rfc-editor.org/info/rfc9552/#section-5.2.1.4";
        type uint32;
    }

    typedef ipv4-interface-identifier {
        reference "https://www.rfc-editor.org/info/rfc5305/#section-3.2";
        type inet:ipv4-address-no-zone;
    }

    typedef ipv6-interface-identifier {
        reference "https://www.rfc-editor.org/info/rfc6119/#section-4.2";
        type inet:ipv6-address-no-zone;
    }

    typedef ospf-interface-identifier {
        reference "https://www.rfc-editor.org/info/rfc9552/#section-5.2.1.4";
        type uint32;
    }

    typedef topology-identifier {
        reference "https://www.rfc-editor.org/info/rfc9552/#section-5.2.2.1";
        type uint16 {
            range "0..4095";
        }
    }

    grouping isis-router-identifier {
        reference "https://www.rfc-editor.org/info/rfc9552/#section-5.2.1.4";
        leaf iso-system-id {
            type netc:iso-system-identifier;
            mandatory true;
        }
    }

    grouping isis-lan-identifier {
        reference "https://www.rfc-editor.org/info/rfc9552/#section-5.2.1.4";
        container is-is-router-identifier {
            uses isis-router-identifier;
        }
        leaf psn {
            type uint8 {
                range "1..255";
            }
            mandatory true;
        }
    }

    grouping ospf-router-identifier {
        reference "https://www.rfc-editor.org/info/rfc9552/#section-5.2.1.4";
        leaf ospf-router-id {
            type uint32;
            mandatory true;
        }
    }

    grouping ospf-v2-lan-identifier {
        reference "https://www.rfc-editor.org/info/rfc9552/#section-5.2.1.4";
        uses ospf-router-identifier;
        leaf ipv4-address {
            type ipv4-interface-identifier;
            mandatory true;
        }
    }

    grouping ospf-v3-lan-identifier {
        reference "https://www.rfc-editor.org/info/rfc9552/#section-5.2.1.4";
        uses ospf-router-identifier;
        leaf lan-interface {
            type ospf-interface-identifier;
            mandatory true;
        }
    }

    grouping node-identifier {
        reference "https://www.rfc-editor.org/info/rfc9552/#section-5.2.1.4";
        leaf as-number {
            type inet:as-number;
        }
        leaf area-id {
            type area-identifier;
        }
        leaf domain-id {
            type domain-identifier;
        }
        choice c-router-identifier {
            case isis-node-case {
                container isis-node {
                    uses isis-router-identifier;
                }
            }
            case isis-pseudonode-case {
                container isis-pseudonode {
                    uses isis-lan-identifier;
                }
            }
            case ospf-node-case {
                container ospf-node {
                    uses ospf-router-identifier;
                }
            }
            case ospf-pseudonode-case {
                container ospf-pseudonode {
                    uses ospf-v3-lan-identifier;
                }
            }
        }
    }

    grouping link-lr-identifiers {
        reference "https://www.rfc-editor.org/info/rfc5307";
        leaf link-local-identifier {
            type uint32;
        }
        leaf link-remote-identifier {
            type uint32;
        }
    }

    grouping prefix-identifiers {
        reference "https://www.rfc-editor.org/info/rfc9552/#section-5.2.3";
        leaf multi-topology-id {
            type topology-identifier;
        }
        leaf ospf-route-type {
            when "../../protocol-id[ .='ospf' or .='ospf-v3' ]";
            type ospf-route-type;
        }
        leaf ip-reachability-information {
            type inet:ip-prefix;
        }
    }

    grouping link-identifier {
        reference "https://www.rfc-editor.org/info/rfc9552/#section-5.2.2";
        uses link-lr-identifiers;
        leaf ipv4-interface-address {
            type ipv4-interface-identifier;
        }
        leaf ipv6-interface-address {
            type ipv6-interface-identifier;
        }
        leaf ipv4-neighbor-address {
            type ipv4-interface-identifier;
        }
        leaf ipv6-neighbor-address {
            type ipv6-interface-identifier;
        }
        leaf multi-topology-id {
            type topology-identifier;
        }
    }

    // BGP Link State top TLV

    grouping linkstate {
        reference "https://www.rfc-editor.org/info/rfc9552/#section-5.2";
        uses bgp-t:route-distinguisher-grouping {
            refine route-distinguisher {
                mandatory false;
            }
        }
        leaf protocol-id {
            type protocol-id;
            mandatory true;
        }
        leaf identifier {
            type identifier;
            mandatory true;
        }
        choice object-type {
            case node-case {
                reference "https://www.rfc-editor.org/info/rfc9552/#section-5.2.1";
                container node-descriptors {
                    uses node-identifier;
                }
            }
            case link-case {
                reference "https://www.rfc-editor.org/info/rfc9552/#section-5.2.2";
                container local-node-descriptors {
                    uses node-identifier;
                    uses bgp-epe:epe-node-descriptors;
                }
                container remote-node-descriptors {
                    uses node-identifier;
                    uses bgp-epe:epe-node-descriptors;
                }
                container link-descriptors {
                    uses link-identifier;
                }
            }
            case prefix-case {
                reference "https://www.rfc-editor.org/info/rfc9552/#section-5.2.3";
                container advertising-node-descriptors {
                    uses node-identifier;
                }
                container prefix-descriptors {
                    uses prefix-identifiers;
                }
            }
            case sr-policy-case {
                reference "https://www.rfc-editor.org/info/rfc9857/#section-8.1";
            }
            case srv6-sid-case {
                reference "https://www.rfc-editor.org/info/rfc9514/#section-6";
                container srv6-node-descriptors {
                    uses node-identifier;
                    uses bgp-epe:epe-node-descriptors;
                }
                container srv6-sid-descriptors {
                    leaf srv6-sid {
                        type bgp-sr:srv6-sid;
                    }
                }
            }
        }
    }

    grouping linkstate-destination {
        list c-linkstate-destination {
            uses linkstate;
            uses bgp-msg:path-id-grouping;
        }
    }

    augment "/bgp-msg:update/bgp-msg:attributes/bgp-mp:mp-reach-nlri/bgp-mp:advertized-routes/bgp-mp:destination-type" {
        case destination-linkstate-case {
            container destination-linkstate {
                uses linkstate-destination;
            }
        }
    }

    augment "/bgp-msg:update/bgp-msg:attributes/bgp-mp:mp-unreach-nlri/bgp-mp:withdrawn-routes/bgp-mp:destination-type" {
        case destination-linkstate-case {
            container destination-linkstate {
                uses linkstate-destination;
            }
        }
    }

    // BGP-LS Node Attributes

    typedef node-flag-bits {
        reference "https://www.rfc-editor.org/info/rfc9552/#section-5.3.1.1";
        type bits {
            bit overload {
                position 0;
            }
            bit attached {
                position 1;
            }
            bit external {
                position 2;
            }
            bit abr {
                position 3;
            }
            bit router {
                position 4;
            }
            bit v6 {
                position 5;
            }
        }
    }

    typedef isis-area-identifier {
        reference "https://www.rfc-editor.org/info/rfc9552/#section-5.3.1.2";
        type binary {
            length "1..20";
        }
    }

    typedef ipv4-router-identifier {
        reference "https://www.rfc-editor.org/info/rfc9552/#section-5.3.1.4";
        type inet:ipv4-address-no-zone;
    }

    typedef ipv6-router-identifier {
        reference "https://www.rfc-editor.org/info/rfc9552/#section-5.3.1.4";
        type inet:ipv6-address-no-zone;
    }

    grouping node-state {
        reference "https://www.rfc-editor.org/info/rfc9552/#section-5.3.1";
        leaf-list topology-identifier {
            type topology-identifier;
        }
        leaf node-flags {
            type node-flag-bits;
        }
        leaf-list isis-area-id {
            type isis-area-identifier;
        }
        leaf dynamic-hostname {
            type string;
        }
        leaf ipv4-router-id {
            type ipv4-router-identifier;
        }
        leaf ipv6-router-id {
            type ipv6-router-identifier;
        }
        leaf ipv4-remote-router-id {
            type ipv4-router-identifier;
        }
        leaf ipv6-remote-router-id {
            type ipv6-router-identifier;
        }
        container segment-routing {
            container sr-mpls-capabilities {
                uses bgp-sr:sr-mpls-attributes;
            }
            container srv6-capabilities {
                uses bgp-sr:srv6-capabilities-tlv;
            }
            list node-msd {
                reference "https://www.rfc-editor.org/info/rfc8814/#section-3";
                uses bgp-sr:msd-tlv;
            }
            container flex-algo-definition {
                uses bgp-sr:flex-algo-definitions;
            }
        }
    }

    // BGP-LS Link Attributes

    typedef link-protection-type {
        reference "https://www.rfc-editor.org/info/rfc5307/#section-1.2";
        type enumeration {
            enum extra-traffic {
                value 1;
            }
            enum unprotected {
                value 2;
            }
            enum shared {
                value 4;
            }
            enum dedicated-1to1 {
                value 8;
            }
            enum dedicated-1plus1 {
                value 16;
            }
            enum enhanced {
                value 32;
            }
        }
    }

    typedef mpls-protocol-mask {
        reference "https://www.rfc-editor.org/info/rfc9552/#section-5.3.2.2";
        type bits {
            bit ldp {
                position 0;
            }
            bit rsvpte {
                position 1;
            }
        }
    }

    typedef administrative-group {
        type uint32;
    }

    grouping unreserved-bandwidth {
        leaf priority {
            type uint8 {
                range "0..7";
            }
        }
        leaf bandwidth {
            type netc:bandwidth;
        }
    }

    typedef delay {
        description "This 24-bit typedef describes delay over a configurable
            interval in microseconds, encoded as an integer value. When set to
            the maximum value 16,777,215 (16.777215 sec), then the delay is at
            least that value, and it may be larger.";
        reference "https://www.rfc-editor.org/info/rfc7471/#section-4.1.5";
        type rt-types:uint24;
        units microseconds;
    }

    typedef loss {
        description "This 24-bit typedef describes packet loss as a percentage
            of the total traffic sent over a configurable interval. The basic
            unit is 0.000003%, where (2^24 - 2) is 50.331642%. This value is
            the highest packet loss percentage that can be expressed.
            Therefore, measured values that are larger than the field maximum
            SHOULD be encoded as the maximum value.";
        reference "https://www.rfc-editor.org/info/rfc7471/#section-4.4.5";
        type rt-types:uint24;
        units percent;
    }

    grouping standard-attributes {
        reference "https://www.rfc-editor.org/info/rfc9552/#section-5.3.2";
        leaf admin-group {
            type administrative-group;
        }
        leaf max-link-bandwidth {
            type netc:bandwidth;
        }
        leaf max-reservable-bandwidth {
            type netc:bandwidth;
        }
        list unreserved-bandwidth {
            key "priority";
            uses unreserved-bandwidth;
        }
        leaf te-metric {
            type netc:te-metric;
        }
        leaf link-protection {
            type link-protection-type;
        }
    }

    grouping sr-attributes {
        list sr-adj-ids {
            reference "https://www.rfc-editor.org/info/rfc9085/#section-2.2.1";
            uses bgp-sr:adj-sid-tlv;
        }
        list sr-lan-adj-ids {
            reference "https://www.rfc-editor.org/info/rfc9085/#section-2.2.2";
            uses bgp-sr:lan-adj-sid-tlv;
        }
        list link-msd {
            reference "https://www.rfc-editor.org/info/rfc8814/#section-4";
            uses bgp-sr:msd-tlv;
        }
    }

    grouping performance-attributes {
        reference "Performance Metric https://www.rfc-editor.org/info/rfc8571/#section-2";
        leaf link-delay {
            description "Unidirectional Link Delay";
            reference "https://www.rfc-editor.org/info/rfc8571/#section-2.1";
            type delay;
        }
        container link-min-max-delay {
            description "Min/Max Unidirectional Link Delay";
            reference "https://www.rfc-editor.org/info/rfc8571/#section-2.2";
            leaf min-delay {
                type delay;
            }
            leaf max-delay {
                type delay;
            }
        }
        leaf delay-variation {
            description "Unidirectional Delay Variation";
            reference "https://www.rfc-editor.org/info/rfc8571/#section-2.3";
            type delay;
        }
        leaf link-loss {
            description "Unidirectional Link Loss";
            reference "https://www.rfc-editor.org/info/rfc8571/#section-2.4";
            type loss;
        }
        leaf residual-bandwidth {
            description "Unidirectional Residual Bandwidth";
            reference "https://www.rfc-editor.org/info/rfc8571/#section-2.5";
            type netc:bandwidth;
        }
        leaf available-bandwidth {
            description "Unidirectional Available Bandwidth";
            reference "https://www.rfc-editor.org/info/rfc8571/#section-2.6";
            type netc:bandwidth;
        }
        leaf utilized-bandwidth {
            description "Unidirectional Utilized Bandwidth";
            reference "https://www.rfc-editor.org/info/rfc8571/#section-2.7";
            type netc:bandwidth;
        }
    }

    grouping l2-bundle-member {
        reference "https://www.rfc-editor.org/info/rfc9085/#section-2.2.3";
        leaf descriptor {
            type uint32;
        }
        container l2-subtlvs {
            uses standard-attributes;
            uses sr-attributes;
            uses performance-attributes;
        }
    }

    typedef abm-length {
        reference "https://www.rfc-editor.org/info/rfc9294/#section-2";
        type enumeration {
            enum zero {
                value 0;
            }
            enum four {
                value 4;
            }
            enum eight {
                value 8;
            }
        }
    }

    grouping asla-bit-mask {
        reference "https://www.rfc-editor.org/info/rfc8919/#section-4.1";
        leaf rsvp-te {
            type boolean;
        }
        leaf sr {
            type boolean;
        }
        leaf lfa {
            type boolean;
        }
        leaf flex-algo {
            type boolean;
        }
    }

    grouping asla-tlv {
        reference "https://www.rfc-editor.org/info/rfc9294/#section-2";
        leaf sabm-length {
            type abm-length;
        }
        leaf udabm-length {
            type abm-length;
        }
        container standard-bit-mask {
            uses asla-bit-mask;
        }
        leaf user-bit-mask {
            type uint64;
        }
        container asla-subtlvs {
            reference "https://www.rfc-editor.org/info/rfc9294/#section-3";
            leaf admin-group {
                type administrative-group;
            }
            leaf te-metric {
                type netc:te-metric;
            }
            leaf-list shared-risk-link-groups {
                type rsvp:srlg-id;
            }
            uses performance-attributes;
            leaf-list extended-admin-group {
                type bgp-sr:extended-admin-group;
            }
        }
    }

    grouping peer-engineering {
        container peer-node-sid {
            description "The SID representing the peer of the BGP session.";
            reference "https://www.rfc-editor.org/info/rfc9086/#section-5";
            uses bgp-sr:epe-sid-tlv;
        }
        container peer-adj-sid {
            description "The SID representing the peer of the BGP session.";
            reference "https://www.rfc-editor.org/info/rfc9086/#section-5";
            uses bgp-sr:epe-sid-tlv;
        }
        list peer-set-sids {
            description "The SID representing the group the peer is part of.";
            reference "https://www.rfc-editor.org/info/rfc9086/#section-5";
            uses bgp-sr:epe-sid-tlv;
        }
    }

    grouping linkstate-attribute {
        reference "https://www.rfc-editor.org/info/rfc9552/#section-5.3.2";
        leaf local-ipv4-router-id {
            type ipv4-router-identifier;
        }
        leaf local-ipv6-router-id {
            type ipv6-router-identifier;
        }
        leaf remote-ipv4-router-id {
            type ipv4-router-identifier;
        }
        leaf remote-ipv6-router-id {
            type ipv6-router-identifier;
        }
        // Link Local/Remote Identifiers MAY be included in the link attribute (see section 5.2.2)
        uses link-lr-identifiers;
        container standard-metric {
            uses standard-attributes;
        }
        leaf mpls-protocol {
            type mpls-protocol-mask;
        }
        leaf metric {
            type netc:metric;
        }
        leaf-list shared-risk-link-groups {
            type rsvp:srlg-id;
        }
        leaf opaque-link {
            type binary;
        }
        leaf link-name {
            type string;
        }
        container sr-attribute {
            uses sr-attributes;
        }
        container egress-peer-engineering {
            uses peer-engineering;
        }
        container srv6 {
            container srv6-end-x-sid {
                reference "https://www.rfc-editor.org/info/rfc9514/#section-4.1";
                uses bgp-sr:srv6-end-x-sid;
            }
            container srv6-lan-end-x-sid {
                reference "https://www.rfc-editor.org/info/rfc9514/#section-4.2";
                uses bgp-sr:srv6-lan-end-x-sid;
            }
        }
        container performance-metric {
            uses performance-attributes;
        }
        container asla-metric {
            reference "https://www.rfc-editor.org/info/rfc9294/#section-2";
            uses asla-tlv;
        }
        leaf-list extended-admin-group {
            reference "https://www.rfc-editor.org/info/rfc9104/#section-2";
            type bgp-sr:extended-admin-group;
        }
        list l2-bundle-member {
            reference "https://www.rfc-editor.org/info/rfc9085/#section-2.2.3";
            uses l2-bundle-member;
        }
    }

    // BGP-LS Prefix Attributes

    typedef route-tag {
        reference "https://www.rfc-editor.org/info/rfc9552/#section-5.3.3.2";
        description "Carries original IGP TAGs of the prefix.";
        type binary {
            length "4";
        }
    }

    typedef extended-route-tag {
        reference "https://www.rfc-editor.org/info/rfc9552/#section-5.3.3.3";
        description "Carries IS-IS Extended Route Tags of the prefix.";
        type binary {
            length "8";
        }
    }

    grouping igp-bits {
        reference "https://www.rfc-editor.org/info/rfc9552/#section-5.3.3.1";
        leaf is-is-up-down {
            type boolean;
        }
        leaf ospf-no-unicast {
            type boolean;
        }
        leaf ospf-local-address {
            type boolean;
        }
        leaf ospf-propagate-nssa {
            type boolean;
        }
    }

    grouping prefix-state {
        reference "https://www.rfc-editor.org/info/rfc9552/#section-5.3.3";
        container igp-bits {
            uses igp-bits;
        }
        leaf-list route-tags {
            type route-tag;
        }
        leaf-list extended-tags {
            type extended-route-tag;
        }
        leaf prefix-metric {
            type netc:igp-metric;
        }
        leaf ospf-forwarding-address {
            type inet:ip-address-no-zone;
        }
        container sr-prefix {
            reference "https://www.rfc-editor.org/info/rfc9085/#section-2.3.1";
            uses bgp-sr:prefix-sid-tlv;
        }
        container sr-range {
            reference "https://www.rfc-editor.org/info/rfc9085/#section-2.3.5";
            uses bgp-sr:range-tlv;
        }
        container flex-algo-prefix-metric {
            reference "https://www.rfc-editor.org/info/rfc9351/#section-3";
            uses bgp-sr:flex-algo-prefix-metric;
        }
        container srv6-locator {
            reference "https://www.rfc-editor.org/info/rfc9514/#section-5.1";
            uses bgp-sr:srv6-locator;
        }
        container attribute-flags {
            reference "https://www.rfc-editor.org/info/rfc9085/#section-2.3.2";
            uses bgp-sr:prefix-attribute-flags;
        }
        leaf source-router-id {
            reference "https://www.rfc-editor.org/info/rfc9085/#section-2.3.3";
            type inet:ip-address-no-zone;
        }
        leaf source-ospf-router-id {
            reference "https://www.rfc-editor.org/info/rfc9085/#section-2.3.4";
            type inet:ipv4-address-no-zone;
        }
    }


    // Link State Path Attributes
    grouping linkstate-path-attribute {
        choice link-state-attribute {
            case node-attributes-case {
                container node-attributes {
                    uses node-state;
                }
            }
            case link-attributes-case {
                container link-attributes {
                    uses linkstate-attribute;
                }
            }
            case prefix-attributes-case {
                container prefix-attributes {
                    uses prefix-state;
                }
            }
            case srv6-sid-attributes-case {
                container srv6-sid-attributes {
                    uses bgp-sr:srv6-attributes;
                }
            }
        }
    }

    grouping linkstate-routes {
        container linkstate-routes {
            list linkstate-route {
                description
                    "Link-state information entry. Due to
                    the complexity of link-state information
                    and YANG limitations this is the top-level
                    object from contract perspective. It is
                    keyed by route-key, whose format is
                    internal to the implementation exposing
                    this information. As an explicit example
                    it can rely on information stored in the
                    entry's subtree, so the subtree MUST NOT
                    be modified by outside entities.
                    Augmentations can attach data, but must
                    be explicitly aware that such data, unlike
                    the data modeled directly here, does not
                    have any effects on keys, especially they
                    must not impact equality tests.";

                key "route-key path-id";

                uses linkstate;
                uses bgp-rib:route {
                    augment attributes {
                        uses linkstate-path-attribute;
                    }
                }
            }
        }
    }

    augment "/bgp-msg:update/bgp-msg:attributes" {
        uses linkstate-path-attribute;
    }

    augment "/bgp-rib:application-rib/bgp-rib:tables/bgp-rib:routes" {
        case linkstate-routes-case {
            uses linkstate-routes;
        }
    }

    augment "/bgp-rib:bgp-rib/bgp-rib:rib/bgp-rib:loc-rib/bgp-rib:tables/bgp-rib:routes" {
        case linkstate-routes-case {
            uses linkstate-routes;
        }
    }

    augment "/bgp-rib:bgp-rib/bgp-rib:rib/bgp-rib:peer/bgp-rib:adj-rib-in/bgp-rib:tables/bgp-rib:routes" {
        case linkstate-routes-case {
            uses linkstate-routes;
        }
    }

    augment "/bgp-rib:bgp-rib/bgp-rib:rib/bgp-rib:peer/bgp-rib:effective-rib-in/bgp-rib:tables/bgp-rib:routes" {
        case linkstate-routes-case {
            uses linkstate-routes;
        }
    }

    augment "/bgp-rib:bgp-rib/bgp-rib:rib/bgp-rib:peer/bgp-rib:adj-rib-out/bgp-rib:tables/bgp-rib:routes" {
        case linkstate-routes-case {
            uses linkstate-routes;
        }
    }

    augment "/bmp-mon:bmp-monitor/bmp-mon:monitor/bmp-mon:router/bmp-mon:peer/bmp-mon:pre-policy-rib/bmp-mon:tables/bmp-mon:routes" {
        case linkstate-routes-case {
            uses linkstate-routes;
        }
    }

    augment "/bmp-mon:bmp-monitor/bmp-mon:monitor/bmp-mon:router/bmp-mon:peer/bmp-mon:post-policy-rib/bmp-mon:tables/bmp-mon:routes" {
        case linkstate-routes-case {
            uses linkstate-routes;
        }
    }
}
