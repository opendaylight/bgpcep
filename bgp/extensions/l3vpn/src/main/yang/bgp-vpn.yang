module bgp-vpn {
    namespace "urn:opendaylight:params:xml:ns:yang:bgp-vpn";
    prefix "bgp-vpn";

    import bgp-labeled-unicast { prefix bgp-lu; revision-date 2018-03-29; }
    import bgp-types { prefix bgp-t; revision-date 2020-01-20; }
    import bgp-rib { prefix bgp-rib; }
    import bgp-message { prefix bgp-msg; revision-date 2020-01-20; }

    organization "Brocade Communications Systems, Inc.";
    contact "Kevin Wang <kwang@brocade.com>";

    description
        "This module contains the base data model of a BGP message.
        It defines the common part of both L3VPN-IPv4 and L3VPN-IPv6 model.

        Copyright (c) 2016 Brocade Communications Systems, Inc. All rights reserved.

        This program and the accompanying materials are made available
        under the terms of the Eclipse Public License v1.0 which
        accompanies this distribution, and is available at
        http://www.eclipse.org/legal/epl-v10.html";

    revision "2018-03-29" {
        description "Add support for add-path for all afi/safi.";
    }

    revision "2017-12-07" {
        description "Add support for add-path in base BGP NLRI.";
    }

    revision 2016-04-13 {
        description "Initial version";
    }

    grouping l3vpn {
        uses bgp-lu:labeled-unicast;
        uses bgp-t:route-distinguisher-grouping;
    }

    grouping l3vpn-ip-destination-type {
        list vpn-destination {
            uses l3vpn;
            uses bgp-msg:path-id-grouping;
        }
    }

    grouping l3vpn-ip-route {
        list vpn-route {
            key "route-key path-id";
            uses l3vpn;
            uses bgp-rib:route;
        }
    }
}
