// vi: set smarttab et sw=4 tabstop=4:
module bgp-state-config {
    yang-version 1;
    namespace "urn:opendaylight:params:xml:ns:yang:bgp-state-config";
    prefix bgp-state-config;

    description
        "This module contains the base YANG definitions for
         BGP State Configuration.
         Copyright (c)2013 Cisco Systems, Inc. All rights reserved.;

         This program and the accompanying materials are made available
         under the terms of the Eclipse Public License v1.0 which
         accompanies this distribution, and is available at
         http://www.eclipse.org/legal/epl-v10.html";

    revision "2016-11-07" {
        description
            "Initial revision.";
    }

    container bgp-state-config {
        leaf config-name {
            type string;
            mandatory true;
        }

        leaf timer {
            type uint16;
            default 5;
        }
    }
}
