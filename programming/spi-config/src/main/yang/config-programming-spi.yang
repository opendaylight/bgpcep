// vi: set smarttab et sw=4 tabstop=4:
module config-programming-spi {
    yang-version 1;
    namespace "urn:opendaylight:params:xml:ns:yang:controller:programming:spi";
    prefix "spi";

    import config { prefix config; revision-date 2013-04-05; }

    organization "Cisco Systems, Inc.";

    contact "Robert Varga <rovarga@cisco.com>";

    description
        "This module contains the base YANG definitions for
         Programming SPI.

        Copyright (c)2013 Cisco Systems, Inc. All rights reserved.;

        This program and the accompanying materials are made available
        under the terms of the Eclipse Public License v1.0 which
        accompanies this distribution, and is available at
        http://www.eclipse.org/legal/epl-v10.html";

    revision "2013-11-15" {
        description
            "Initial revision";
    }

    identity instruction-scheduler {
        description
            "Service representing an instruction scheduler.";

        base "config:service-type";
        config:java-class "org.opendaylight.bgpcep.programming.spi.InstructionScheduler";
    }
}
