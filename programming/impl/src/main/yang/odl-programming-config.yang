// vi: set smarttab et sw=4 tabstop=4:
module odl-programming-config {
    yang-version 1;
    namespace "urn:opendaylight:params:xml:ns:yang:odl:programming:config";
    prefix odl-programming-config;

    description
        "This module contains the base YANG definitions for
         Programming Configuration.
         Copyright (c) 2017 Pantheon Technologies s.r.o. and others.  All rights reserved.

         This program and the accompanying materials are made available
         under the terms of the Eclipse Public License v1.0 which
         accompanies this distribution, and is available at
         http://www.eclipse.org/legal/epl-v10.html";

    organization "Pantheon Technologies";
    contact "Claudio D. Gasparini <claudio.gasparini@pantheon.sk>";

    revision "2017-03-01" {
        description
            "Initial revision.";
    }

    container odl-programming {
        list odl-programming-config {
            key "instruction-queue-id";
            leaf instruction-queue-id {
                type string;
            }
        }
    }
}
