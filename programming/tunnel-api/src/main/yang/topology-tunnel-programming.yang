module topology-tunnel-programming {
    yang-version 1;
    namespace "urn:opendaylight:params:xml:ns:yang:topology:tunnel:programming";
    prefix "ttp";

    import network-topology { prefix nt; revision-date 2013-10-21; }
    import network-topology-programming { prefix tp; revision-date 2013-11-02; }

    organization "Cisco Systems, Inc.";
    contact "Robert Varga <rovarga@cisco.com>";

    description
        "This module contains the programming extensions for tunnel
        topologies.

        Copyright (c)2013 Cisco Systems, Inc. All rights reserved.

        This program and the accompanying materials are made available
        under the terms of the Eclipse Public License v1.0 which
        accompanies this distribution, and is available at
        http://www.eclipse.org/legal/epl-v10.html";

    revision "2013-09-30" {
        description
            "Initial revision.";
        reference "";
    }

    grouping base-tunnel-input {
        uses tp:topology-instruction-input;

        leaf link-id {
            type nt:link-id;
            mandatory true;
        }
    }

    grouping base-tunnel-output {
        uses tp:topology-instruction-output;
    }

    grouping create-tunnel-input {
        uses tp:topology-instruction-input;
    }

    grouping create-tunnel-output {
        uses base-tunnel-output;

        leaf link-id {
            type nt:link-id;
            mandatory true;
        }
    }

    grouping destroy-tunnel-input {
        uses base-tunnel-input;
    }

    grouping destroy-tunnel-output {
        uses base-tunnel-output;
    }

    grouping tp-reference {
        leaf node {
            type nt:node-ref;
            mandatory true;
        }
        leaf tp {
            type nt:tp-ref;
            mandatory true;
        }
    }

    grouping create-p2p-tunnel-input {
        uses create-tunnel-input;

        container destination {
            uses tp-reference;
        }
        container source {
            uses tp-reference;
        }
    }

    grouping create-p2p-tunnel-output {
        uses create-tunnel-output;
    }
}
